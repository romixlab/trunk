int firstChar_0 = 32;
int capital_0 =  21, baseline_0 = 0, bottom_0 = 0;
string widths_0 = "13,5,11,20,21,17,23,7,13,13,15,23,7,23,6,19,19,9,19,17,20,18,18,19,18,18,7,7,21,23,21,17,21,21,19,20,19,18,18,20,19,5,15,19,17,21,19,21,17,21,17,19,19,19,21,25,19,21,19,12,19,12,21,29,7,17,17,17,17,17,12,17,16,7,11,16,5,27,16,18,17,17,13,15,13,16,17,21,16,18,16,13,5,13,25,17,0,0,6,0,7,4,10,3,14,18,5,8,2,13,11,0,3,7,7,11,11,16,13,15,16,19,4,22,8,19,16,18,16,9,12,13,11,10,14,2,18,8,2,20,13,9,9,11,11,19,6,17,5,3,8,13,17,32,3,20,10,12,12,0,21,19,19,18,25,18,31,20,19,19,19,21,21,19,21,20,17,20,19,21,25,19,23,18,29,33,23,23,18,20,26,18,18,18,18,16,21,17,27,16,16,16,17,17,19,16,18,18,17,17,17,17,29,17,21,17,25,28,22,22,18,16,22,17";

string draw_0 = "M|13|4!"
	"M|3|25*D|3|11*M|3|6*D|3|4*M|0|21!"
	"M|5|25*D|5|21*D|3|19*M|9|25*D|9|21*D|7|19*M|0|21!"
	"M|11|29*D|4|-3*M|17|29*D|10|-3*M|4|16*D|18|16*M|3|5*D|17|5*M|0|21!"
	"M|3|8*D|7|4*D|15|4*D|19|8*D|19|12*D|15|16*D|7|16*D|3|20*D|3|24*D|7|28*D|15|28*D|18|24*M|11|29*D|11|3*M|0|21!"
	"M|4|23*D|8|23*D|8|19*D|4|19*D|4|23*M|3|4*D|15|23*M|10|8*D|14|8*D|14|4*D|10|4*D|10|8*M|0|21!"
	"M|21|4*D|5|18*D|5|23*D|7|25*D|10|25*D|12|23*D|12|18*D|3|12*D|3|7*D|6|4*D|13|4*D|21|12*M|0|21!"
	"M|5|25*D|5|21*D|3|19*M|0|21!"
	"M|11|29*D|6|24*D|3|15*D|3|11*D|6|2*D|11|-3*M|0|21!"
	"M|3|29*D|8|24*D|11|15*D|11|11*D|8|2*D|3|-3*M|0|21!"
	"M|8|19*D|8|7*M|3|16*D|13|10*M|13|16*D|3|10*M|0|21!"
	"M|12|22*D|12|4*M|3|13*D|21|13*M|0|21!"
	"M|5|4*D|5|6*D|3|6*D|3|4*D|5|4*D|3|0*M|0|21!"
	"M|3|13*D|21|13*M|0|21!"
	"M|4|6*D|3|6*D|3|4*D|5|4*D|5|6*D|4|6*M|0|21!"
	"M|3|4*D|17|25*M|0|21!"
	"M|3|10*D|3|21*D|7|25*D|13|25*D|17|21*D|17|8*D|13|4*D|7|4*D|3|8*D|3|10*M|3|8*D|17|21*M|0|21!"
	"M|3|21*D|7|25*D|7|4*M|0|21!"
	"M|4|21*D|8|25*D|12|25*D|16|21*D|16|17*D|3|4*D|17|4*M|0|21!"
	"M|3|21*D|7|25*D|12|25*D|15|22*D|15|17*D|13|15*D|8|15*M|13|15*D|15|13*D|15|7*D|12|4*D|7|4*D|3|8*M|0|21!"
	"M|13|4*D|13|25*D|3|11*D|18|11*M|0|21!"
	"M|15|25*D|4|25*D|4|16*D|8|18*D|12|18*D|16|14*D|16|8*D|12|4*D|7|4*D|3|8*M|0|21!"
	"M|16|22*D|13|25*D|9|25*D|8|25*D|3|20*D|3|8*D|7|4*D|12|4*D|16|8*D|16|12*D|12|16*D|7|16*D|3|12*M|0|21!"
	"M|7|4*D|17|25*D|3|25*M|0|21!"
	"M|7|16*D|12|16*D|15|19*D|15|22*D|12|25*D|7|25*D|4|22*D|4|19*D|7|16*D|3|12*D|3|8*D|7|4*D|12|4*D|16|8*D|16|12*D|12|16*M|0|21!"
	"M|3|8*D|7|4*D|12|4*D|16|8*D|16|21*D|12|25*D|7|25*D|3|21*D|3|17*D|7|13*D|12|13*D|16|17*M|0|21!"
	"M|5|18*D|3|18*D|3|16*D|5|16*D|5|18*M|5|6*D|3|6*D|3|4*D|5|4*D|5|6*M|0|21!"
	"M|5|18*D|3|18*D|3|16*D|5|16*D|5|18*M|5|4*D|5|6*D|3|6*D|3|4*D|5|4*D|3|1*M|0|21!"
	"M|19|22*D|3|13*D|19|4*M|0|21!"
	"M|3|16*D|21|16*M|3|10*D|21|10*M|0|21!"
	"M|3|22*D|19|13*D|3|4*M|0|21!"
	"M|3|21*D|7|25*D|11|25*D|15|21*D|15|17*D|9|11*D|9|8*M|9|4*D|9|6*M|0|21!"
	"M|14|19*D|10|19*D|7|16*D|7|13*D|9|11*D|12|11*D|14|13*D|14|15*M|14|13*D|14|10*D|16|10*D|19|13*D|19|19*D|13|25*D|9|25*D|3|19*D|3|9*D|8|4*D|15|4*D|19|8*M|0|21!"
	"M|19|4*D|11|25*D|3|4*M|6|11*D|16|11*M|0|21!"
	"M|3|15*D|13|15*D|16|18*D|16|22*D|13|25*D|3|25*D|3|4*D|14|4*D|17|7*D|17|11*D|13|15*M|0|21!"
	"M|18|21*D|14|25*D|7|25*D|3|21*D|3|8*D|7|4*D|14|4*D|18|8*M|0|21!"
	"M|3|4*D|3|25*D|12|25*D|17|20*D|17|9*D|12|4*D|3|4*M|0|21!"
	"M|16|25*D|3|25*D|3|4*D|16|4*M|3|15*D|11|15*M|0|21!"
	"M|16|25*D|3|25*D|3|4*M|3|15*D|11|15*M|0|21!"
	"M|18|21*D|14|25*D|7|25*D|3|21*D|3|8*D|7|4*D|14|4*D|18|8*D|18|14*D|10|14*M|0|21!"
	"M|3|25*D|3|4*M|17|25*D|17|4*M|3|15*D|17|15*M|0|21!"
	"M|3|25*D|3|4*M|0|21!"
	"M|13|25*D|13|7*D|10|4*D|6|4*D|3|7*D|3|11*M|0|21!"
	"M|3|25*D|3|4*M|17|25*D|3|11*M|8|16*D|17|4*M|0|21!"
	"M|3|25*D|3|4*D|15|4*M|0|21!"
	"M|19|4*D|19|25*D|11|4*D|3|25*D|3|4*M|0|21!"
	"M|17|25*D|17|4*D|3|25*D|3|4*M|0|21!"
	"M|8|4*D|14|4*D|19|9*D|19|20*D|14|25*D|8|25*D|3|20*D|3|9*D|8|4*M|0|21!"
	"M|3|4*D|3|25*D|12|25*D|15|22*D|15|17*D|12|14*D|3|14*M|0|21!"
	"M|8|25*D|3|20*D|3|9*D|8|4*D|14|4*D|19|9*D|19|20*D|14|25*D|8|25*M|12|8*D|18|2*M|0|21!"
	"M|3|4*D|3|25*D|12|25*D|15|22*D|15|17*D|12|14*D|3|14*M|5|14*D|15|4*M|0|21!"
	"M|17|22*D|14|25*D|7|25*D|3|21*D|3|18*D|6|15*D|13|15*D|17|11*D|17|8*D|13|4*D|7|4*D|3|8*M|0|21!"
	"M|10|25*D|10|4*M|3|25*D|17|25*M|0|21!"
	"M|3|25*D|3|8*D|7|4*D|13|4*D|17|8*D|17|25*M|0|21!"
	"M|3|25*D|11|4*D|19|25*M|0|21!"
	"M|3|25*D|8|4*D|13|25*D|18|4*D|23|25*M|0|21!"
	"M|3|25*D|17|4*M|17|25*D|3|4*M|0|21!"
	"M|3|25*D|11|15*D|11|4*M|19|25*D|11|15*M|0|21!"
	"M|3|25*D|17|25*D|3|4*D|17|4*M|0|21!"
	"M|10|29*D|3|29*D|3|-3*D|10|-3*M|0|21!"
	"M|3|25*D|17|4*M|0|21!"
	"M|3|29*D|10|29*D|10|-3*D|3|-3*M|0|21!"
	"M|3|18*D|11|25*D|19|18*M|0|21!"
	"M|3|-3*D|27|-3*M|0|21!"
	"M|3|25*D|3|21*D|5|19*M|0|21!"
	"M|4|18*D|12|18*D|15|15*D|15|4*M|15|8*D|11|4*D|6|4*D|3|7*D|3|8*D|6|11*D|13|11*D|15|9*M|0|21!"
	"M|3|25*D|3|4*D|12|4*D|15|7*D|15|12*D|12|15*D|3|15*M|0|21!"
	"M|15|15*D|12|18*D|6|18*D|3|15*D|3|7*D|6|4*D|12|4*D|15|7*M|0|21!"
	"M|15|25*D|15|4*D|6|4*D|3|7*D|3|12*D|6|15*D|15|15*M|0|21!"
	"M|15|6*D|13|4*D|6|4*D|3|7*D|3|15*D|6|18*D|12|18*D|15|15*D|15|12*D|14|11*D|3|11*M|0|21!"
	"M|10|25*D|6|21*D|6|4*M|3|17*D|9|17*M|0|21!"
	"M|15|7*D|12|4*D|7|4*D|3|8*D|3|14*D|7|18*D|12|18*D|15|15*D|15|0*D|12|-3*D|8|-3*D|5|0*M|0|21!"
	"M|3|25*D|3|4*M|3|15*D|6|18*D|11|18*D|14|15*D|14|4*M|0|21!"
	"M|3|26*D|3|24*D|5|24*D|5|26*D|3|26*M|4|18*D|4|4*M|0|21!"
	"M|7|26*D|7|24*D|9|24*D|9|26*D|7|26*M|8|18*D|8|0*D|5|-3*D|3|-3*M|0|21!"
	"M|3|25*D|3|4*M|13|18*D|3|8*M|7|12*D|14|4*M|0|21!"
	"M|3|25*D|3|4*M|0|21!"
	"M|3|18*D|3|4*M|3|14*D|6|17*D|11|17*D|14|14*D|14|4*M|14|14*D|17|17*D|22|17*D|25|14*D|25|4*M|0|21!"
	"M|3|18*D|3|4*M|3|14*D|6|17*D|11|17*D|14|14*D|14|4*M|0|21!"
	"M|6|18*D|3|15*D|3|7*D|6|4*D|13|4*D|16|7*D|16|15*D|13|18*D|6|18*M|0|21!"
	"M|3|-3*D|3|18*M|3|15*D|6|18*D|12|18*D|15|15*D|15|7*D|12|4*D|6|4*D|3|7*M|0|21!"
	"M|15|18*D|15|-3*M|15|15*D|12|18*D|6|18*D|3|15*D|3|7*D|6|4*D|12|4*D|15|7*M|0|21!"
	"M|3|18*D|3|4*M|3|13*D|7|17*D|11|17*M|0|21!"
	"M|13|16*D|11|18*D|5|18*D|3|16*D|3|13*D|5|11*D|11|11*D|13|9*D|13|6*D|11|4*D|5|4*D|3|6*M|0|21!"
	"M|6|25*D|6|7*D|9|4*D|11|4*M|3|18*D|10|18*M|0|21!"
	"M|3|18*D|3|7*D|6|4*D|10|4*D|14|8*M|14|18*D|14|4*M|0|21!"
	"M|3|18*D|9|4*D|15|18*M|0|21!"
	"M|3|18*D|7|4*D|11|18*D|15|4*D|19|18*M|0|21!"
	"M|3|18*D|14|4*M|14|18*D|3|4*M|0|21!"
	"M|4|18*D|10|4*M|16|18*D|7|-3*D|3|-3*M|0|21!"
	"M|3|18*D|14|18*D|3|4*D|14|4*M|0|21!"
	"M|11|29*D|9|29*D|6|26*D|6|16*D|3|13*D|6|10*D|6|0*D|9|-3*D|11|-3*M|0|21!"
	"M|3|29*D|3|-3*M|0|21!"
	"M|3|29*D|5|29*D|8|26*D|8|16*D|11|13*D|8|10*D|8|0*D|5|-3*D|3|-3*M|0|21!"
	"M|3|16*D|8|21*D|10|21*D|16|15*D|18|15*D|23|20*M|0|21!"
	"M|3|11*D|3|4*D|15|4*D|15|11*D|9|20*D|3|11*M|0|21!"
	"M|0|4!"
	"M|0|4!"
	"M|6|4!"
	"M|0|4!"
	"M|7|4!"
	"M|4|4!"
	"M|10|4!"
	"M|3|4!"
	"M|14|4!"
	"M|18|4!"
	"M|5|4!"
	"M|8|4!"
	"M|2|4!"
	"M|13|4!"
	"M|11|4!"
	"M|0|4!"
	"M|3|4!"
	"M|3|19*D|3|23*D|5|25*M|0|21!"
	"M|5|25*D|5|21*D|3|19*M|0|21!"
	"M|5|25*D|3|23*D|3|19*M|7|19*D|7|23*D|9|25*M|0|21!"
	"M|5|25*D|5|21*D|3|19*M|9|25*D|9|21*D|7|19*M|0|21!"
	"M|16|4!"
	"M|13|4!"
	"M|15|4!"
	"M|16|4!"
	"M|19|4!"
	"M|4|4!"
	"M|4|14*D|5|11*D|7|9*D|9|8*D|12|8*D|14|9*D|16|11*D|17|14*D|16|17*D|14|19*D|12|20*D|9|20*D|7|19*D|5|17*D|4|14*M|3|7*D|19|21*M|0|21!"
	"M|8|4!"
	"M|19|4!"
	"M|16|4!"
	"M|18|4!"
	"M|16|4!"
	"M|9|4!"
	"M|12|4!"
	"M|13|4!"
	"M|11|4!"
	"M|10|4!"
	"M|14|4!"
	"M|2|4!"
	"M|16|25*D|3|25*D|3|4*D|16|4*M|3|15*D|11|15*M|5|27*D|6|27*D|6|28*D|5|28*D|5|27*M|11|27*D|12|27*D|12|28*D|11|28*D|11|27*M|0|21!"
	"M|8|4!"
	"M|2|4!"
	"M|10|21*D|3|15*D|10|9*M|18|21*D|11|15*D|18|9*M|0|21!"
	"M|13|4!"
	"M|9|4!"
	"M|9|4!"
	"M|11|4!"
	"M|5|17*D|3|19*D|3|21*D|5|23*D|7|23*D|9|21*D|9|19*D|7|17*D|5|17*M|0|21!"
	"M|3|6*D|17|6*M|10|9*D|10|23*M|17|16*D|3|16*M|0|21!"
	"M|6|4!"
	"M|17|4!"
	"M|5|4!"
	"M|3|4!"
	"M|8|4!"
	"M|13|4!"
	"M|15|6*D|13|4*D|6|4*D|3|7*D|3|15*D|6|18*D|12|18*D|15|15*D|15|12*D|14|11*D|3|11*M|5|21*D|5|20*D|6|20*D|6|21*D|5|21*M|11|20*D|12|20*D|12|21*D|11|21*D|11|20*M|0|21!"
	"M|17|25*D|17|4*D|3|25*D|3|4*M|26|14*D|24|14*D|22|16*D|22|18*D|24|20*D|26|20*D|28|18*D|28|16*D|26|14*M|28|10*D|22|10*M|0|21!"
	"M|3|4!"
	"M|11|21*D|18|15*D|11|9*M|3|21*D|10|15*D|3|9*M|0|21!"
	"M|10|4!"
	"M|12|4!"
	"M|12|4!"
	"M|0|4!"
	"M|19|4*D|11|25*D|3|4*M|6|11*D|16|11*M|0|21!"
	"M|3|16*D|13|16*D|17|12*D|17|7*D|14|4*D|3|4*D|3|25*D|16|25*M|0|21!"
	"M|3|15*D|13|15*D|16|18*D|16|22*D|13|25*D|3|25*D|3|4*D|14|4*D|17|7*D|17|11*D|13|15*M|0|21!"
	"M|16|25*D|3|25*D|3|4*M|0|21!"
	"M|6|4*D|6|20*D|11|25*D|20|25*D|20|4*M|23|-3*D|23|4*D|3|4*D|3|-3*M|0|21!"
	"M|16|25*D|3|25*D|3|4*D|16|4*M|3|15*D|11|15*M|0|21!"
	"M|4|25*D|16|13*D|28|25*M|3|4*D|14|15*M|18|15*D|29|4*M|16|25*D|16|4*M|0|21!"
	"M|3|8*D|7|4*D|14|4*D|18|8*D|18|12*D|14|15*D|17|18*D|17|22*D|14|25*D|7|25*D|3|21*M|12|15*D|14|15*M|0|21!"
	"M|17|25*D|17|4*M|3|25*D|3|4*M|3|7*D|17|21*M|0|21!"
	"M|17|25*D|17|4*M|3|25*D|3|4*M|3|7*D|17|21*M|8|26*D|12|26*M|0|21!"
	"M|3|25*D|3|4*M|3|11*D|17|25*M|17|4*D|8|16*M|0|21!"
	"M|3|4*D|11|25*D|19|4*M|0|21!"
	"M|19|4*D|19|25*D|11|7*D|3|25*D|3|4*M|0|21!"
	"M|3|25*D|3|4*M|17|4*D|17|25*M|3|15*D|17|15*M|0|21!"
	"M|8|4*D|14|4*D|19|9*D|19|20*D|14|25*D|8|25*D|3|20*D|3|9*D|8|4*M|0|21!"
	"M|18|4*D|18|25*D|3|25*D|3|4*M|0|21!"
	"M|3|4*D|3|25*D|12|25*D|15|22*D|15|17*D|12|14*D|3|14*M|0|21!"
	"M|18|21*D|14|25*D|7|25*D|3|21*D|3|8*D|7|4*D|14|4*D|18|8*M|0|21!"
	"M|10|25*D|10|4*M|3|25*D|17|25*M|0|21!"
	"M|19|25*D|19|9*D|14|4*D|7|4*D|3|8*M|3|25*D|3|16*D|7|12*D|16|12*D|19|15*M|0|21!"
	"M|13|25*D|13|4*M|3|14*D|3|18*D|7|22*D|19|22*D|23|18*D|23|13*D|18|9*D|7|9*D|3|13*D|3|14*M|0|21!"
	"M|4|25*D|17|4*M|3|4*D|16|25*M|0|21!"
	"M|21|-3*D|21|4*D|3|4*D|3|25*M|18|25*D|18|4*M|0|21!"
	"M|16|14*D|7|14*D|3|18*D|3|25*M|16|25*D|16|4*M|0|21!"
	"M|27|25*D|27|4*D|3|4*D|3|25*M|15|4*D|15|25*M|0|21!"
	"M|31|-3*D|31|4*D|3|4*D|3|25*M|15|4*D|15|25*M|27|4*D|27|25*M|0|21!"
	"M|8|15*D|17|15*D|21|11*D|21|8*D|17|4*D|8|4*D|8|25*D|3|25*D|3|24*M|0|21!"
	"M|3|15*D|12|15*D|16|11*D|16|8*D|12|4*D|3|4*D|3|25*M|21|4*D|21|25*M|0|21!"
	"M|3|15*D|12|15*D|16|11*D|16|8*D|12|4*D|3|4*D|3|25*M|0|21!"
	"M|3|8*D|7|4*D|14|4*D|18|8*D|18|21*D|14|25*D|7|25*D|3|21*M|12|15*D|18|15*M|0|21!"
	"M|3|25*D|3|4*M|8|12*D|8|20*D|13|25*D|19|25*D|24|20*D|24|9*D|19|4*D|13|4*D|8|9*D|8|12*M|3|15*D|8|15*M|8|17*D|8|20*M|0|21!"
	"M|16|14*D|7|14*D|3|18*D|3|21*D|7|25*D|16|25*D|16|4*M|3|4*D|9|14*M|0|21!"
	"M|16|4*D|16|18*M|16|14*D|12|18*D|7|18*D|3|14*D|3|8*D|7|4*D|12|4*D|16|8*M|0|21!"
	"M|15|25*D|12|25*D|11|24*D|7|24*D|3|20*D|3|7*D|6|4*D|13|4*D|16|7*D|16|15*D|13|18*D|6|18*D|3|15*M|0|21!"
	"M|12|12*D|14|14*D|14|16*D|12|18*D|3|18*D|3|4*D|12|4*D|16|7*D|16|9*D|13|12*D|3|12*M|0|21!"
	"M|14|18*D|3|18*D|3|4*M|0|21!"
	"M|19|-1*D|19|4*D|3|4*D|3|-1*M|17|4*D|17|18*D|11|18*D|5|12*D|5|4*M|0|21!"
	"M|15|6*D|13|4*D|6|4*D|3|7*D|3|15*D|6|18*D|12|18*D|15|15*D|15|12*D|14|11*D|3|11*M|0|21!"
	"M|14|18*D|14|4*M|3|4*D|10|12*M|4|18*D|14|8*D|24|18*M|25|4*D|18|12*M|0|21!"
	"M|5|16*D|7|18*D|11|18*D|13|16*D|13|14*D|11|12*D|14|9*D|14|7*D|11|4*D|6|4*D|3|7*M|9|12*D|11|12*M|0|21!"
	"M|3|18*D|3|4*M|14|4*D|14|18*M|3|5*D|14|16*M|0|21!"
	"M|3|18*D|3|4*M|14|4*D|14|18*M|7|21*D|7|20*D|10|20*D|10|21*D|7|21*M|3|5*D|14|16*M|0|21!"
	"M|3|18*D|3|4*M|14|18*D|3|7*M|15|4*D|8|12*M|0|21!"
	"M|3|4*D|5|6*D|5|14*D|9|18*D|15|18*D|15|4*M|0|21!"
	"M|3|4*D|3|18*D|10|6*D|17|18*D|17|4*M|0|21!"
	"M|3|18*D|3|4*M|14|18*D|14|4*M|14|11*D|3|11*M|0|21!"
	"M|16|14*D|12|18*D|7|18*D|3|14*D|3|8*D|7|4*D|12|4*D|16|8*D|16|14*M|0|21!"
	"M|16|4*D|16|18*D|3|18*D|3|4*M|0|21!"
	"M|3|-3*D|3|18*M|3|14*D|7|18*D|11|18*D|15|14*D|15|8*D|11|4*D|7|4*D|3|8*M|0|21!"
	"M|15|15*D|12|18*D|6|18*D|3|15*D|3|7*D|6|4*D|12|4*D|15|7*M|0|21!"
	"M|9|18*D|9|4*M|3|18*D|15|18*M|0|21!"
	"M|3|18*D|9|4*D|6|-3*M|15|18*D|9|4*M|0|21!"
	"M|15|24*D|15|-3*M|11|18*D|6|18*D|3|15*D|3|7*D|6|4*D|12|4*D|15|7*D|18|4*D|24|4*D|27|7*D|27|15*D|24|18*D|18|18*D|15|15*D|12|18*D|11|18*M|0|21!"
	"M|4|18*D|15|4*M|14|18*D|3|4*M|0|21!"
	"M|19|-1*D|19|4*D|3|4*D|3|18*M|16|18*D|16|4*M|0|21!"
	"M|3|18*D|3|13*D|6|10*D|13|10*D|15|12*M|15|4*D|15|18*M|0|21!"
	"M|23|18*D|23|4*D|3|4*D|3|18*M|13|4*D|13|18*M|0|21!"
	"M|26|-1*D|26|4*D|3|4*D|3|18*M|13|4*D|13|18*M|23|18*D|23|4*M|0|21!"
	"M|7|12*D|17|12*D|20|9*D|20|7*D|17|4*D|7|4*D|7|18*D|3|18*D|3|17*M|0|21!"
	"M|3|18*D|3|4*D|13|4*D|16|7*D|16|9*D|13|12*D|3|12*M|20|4*D|20|18*M|0|21!"
	"M|3|18*D|3|4*D|13|4*D|16|7*D|16|9*D|13|12*D|3|12*M|0|21!"
	"M|3|15*D|6|18*D|11|18*D|14|15*D|14|7*D|11|4*D|6|4*D|3|7*M|9|11*D|14|11*M|0|21!"
	"M|7|12*D|7|7*D|10|4*D|17|4*D|20|7*D|20|15*D|17|18*D|10|18*D|7|15*D|7|12*M|3|4*D|3|18*M|3|11*D|7|11*M|15|18*D|16|18*M|0|21!"
	"M|15|11*D|6|11*D|3|14*D|3|15*D|6|18*D|15|18*D|15|4*M|3|4*D|10|11*M|0|21";
