// vim:  set foldmethod=marker commentstring=//\ %s :

#include "font0.ulp"
#include "font1.ulp"
#include "font2.ulp"

int nCodes = 224;


real size = 0.2;

string str;

int i, j;

int fontNumber = 0;
int rotation = 0;
int mirror = 0;
string out = "SET WIRE_BEND 2; ";
string draw[];
string widths[];

int capital;
int firstChar;

real translate(int x)
{
	return (real(x) / capital) * size;
}

real translateX(real x, real y)
{
	if (rotation == 1) {
		if (mirror) {
			return y;
		}
		return -y;
	}
	if (rotation == 2) {
		return -x;
	}
	if (rotation == 3) {
		if (mirror) {
			return -y;
		}
		return y;
	}
	return x;
}

real translateY(real x, real y)
{
	if (rotation == 1) {
		return x;
	}
	if (rotation == 2) {
		if (mirror) {
			return y;
		}
		return -y;
	}
	if (rotation == 3) {
		return -x;
	}
	if (mirror) {
		return -y;
	}
	return y;
}

int result = dlgDialog("Russian text") {
	dlgGridLayout {
		dlgCell(0,0) {
			dlgLabel("String");
		}
		dlgCell(0,1, 0,3) {
			dlgStringEdit(str);
		}
		dlgCell(1,0) {
			dlgLabel("Size");
		}
		dlgCell(1,1) {
			dlgRealEdit(size);
		}
		dlgCell(1,2, 1, 3) {
			dlgCheckBox("Mirror", mirror);
		}
		dlgCell(2,0, 2, 1) {
			dlgGroup("Font") {
				dlgRadioButton("Font 1", fontNumber);
				dlgRadioButton("Font 2", fontNumber);
				dlgRadioButton("Font 3", fontNumber);
			}
		}
		dlgCell(2,2, 2, 3) {
			dlgGroup("Rotation") {
				dlgRadioButton("0", rotation);
				dlgRadioButton("90", rotation);
				dlgRadioButton("180", rotation);
				dlgRadioButton("270", rotation);
			}
		}
		dlgCell(3,0, 3, 1) {
			dlgPushButton("+&Accept") dlgAccept();
		}
		dlgCell(3,2, 3, 3) {
			dlgPushButton("-Cancel") dlgReject();
		}
	}
};

if (result != 1) {
	exit(0);
}

if (fontNumber == 0) {
	capital = capital_0;
	firstChar = firstChar_0;
	strsplit(widths, widths_0, ',');
	strsplit(draw, draw_0, '!');
}

if (fontNumber == 2) {
	capital = capital_2;
	firstChar = firstChar_2;
	strsplit(widths, widths_2, ',');
	strsplit(draw, draw_2, '!');
}

if (fontNumber == 1) {
	capital = capital_1;
	firstChar = firstChar_1;
	strsplit(widths, widths_1, ',');
	strsplit(draw, draw_1, '!');
}

real startX = translate(0), startY = translate(0);

for (i = 0; i < strlen(str); i++) {
	string c = strsub(str, i, 1);
	int code = 63;
	for (j = 0; j < nCodes*2; j+=2) {
		if (codes[j] ==c) {
			code = strtol(codes[j+1]);
			break;
		}
	}
	code -= firstChar;
	int width = strtol(widths[code]);
	string parts[];
	int nParts = strsplit(parts, draw[code], '*');
	real curX = startX;
	real curY = startY;
	for (j = 0; j < nParts; j++) {
		string command[];
		strsplit(command, parts[j], '|');
		int x = strtol(command[1]);
		int y = strtol(command[2]);
		if (command[0] == "D") {
			string buf;
			real tempX = startX + translate(x);
			real tempY =  startY + translate(y);
			sprintf(buf, "WIRE (R %f %f) (R %f %f);", translateX(curX, curY), translateY(curX, curY), translateX(tempX, tempY), translateY(tempX, tempY));
			out += buf;
		}
		curX = startX + translate(x);
		curY = startY + translate(y);
	}
	startX += translate(width);
}

exit(out);
