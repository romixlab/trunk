int firstChar_2 = 32;

int capital_2 =  21, baseline_2 = 0, bottom_2 = 0;

string widths_2 = "13,8,10,20,19,18,25,10,13,12,15,24,6,24,8,19,19,13,19,19,20,19,19,19,19,18,8,8,22,24,22,17,21,19,20,20,20,19,19,20,20,6,14,20,18,22,20,21,20,21,20,19,17,20,19,24,19,19,19,13,19,12,21,24,10,17,18,17,17,17,12,17,17,7,9,17,6,28,17,18,18,17,14,16,12,17,16,21,16,16,16,11,6,12,25,14,0,0,6,0,7,4,10,3,14,18,5,8,2,13,11,0,3,6,6,10,10,16,13,15,16,19,4,17,8,19,16,18,16,9,12,13,11,10,14,2,18,8,2,19,13,9,9,11,11,17,6,17,5,3,8,13,16,31,3,19,10,12,12,0,19,19,19,17,23,18,32,18,19,19,19,19,21,19,20,19,19,19,17,20,24,18,20,18,23,25,19,21,19,19,23,18,16,17,17,15,21,16,26,16,16,16,16,17,19,16,17,18,17,16,15,15,26,15,20,14,27,29,17,19,16,17,21,15";

string draw_2 = "M|13|4!"
	"M|5|25*D|5|11*M|5|6*D|4|5*D|5|4*D|6|5*D|5|6*M|0|21!"
	"M|3|23*D|2|24*D|3|25*D|4|24*D|4|22*D|3|20*D|2|19*M|7|23*D|6|24*D|7|25*D|8|24*D|8|22*D|7|20*D|6|19*M|0|21!"
	"M|11|29*D|4|-3*M|17|29*D|10|-3*M|4|16*D|18|16*M|3|10*D|17|10*M|0|21!"
	"M|8|29*D|8|0*M|12|29*D|12|0*M|17|22*D|15|24*D|12|25*D|8|25*D|5|24*D|3|22*D|3|20*D|4|18*D|5|17*D|7|16*D|13|14*D|15|13*D|16|12*D|17|10*D|17|7*D|15|5*D|12|4*D|8|4*D|5|5*D|3|7*M|0|21!"
	"M|7|23*D|9|21*D|7|19*D|5|21*D|7|23*M|13|8*D|15|6*D|13|4*D|11|6*D|13|8*M|4|4*D|16|23*M|0|21!"
	"M|23|16*D|23|17*D|22|18*D|21|18*D|20|17*D|19|15*D|17|10*D|15|7*D|13|5*D|11|4*D|7|4*D|5|5*D|4|6*D|3|8*D|3|10*D|4|12*D|5|13*D|12|17*D|13|18*D|14|20*D|14|22*D|13|24*D|11|25*D|9|24*D|8|22*D|8|20*D|9|17*D|11|14*D|16|7*D|18|5*D|20|4*D|22|4*D|23|5*D|23|6*M|0|21!"
	"M|8|25*D|3|19*D|6|25*D|8|25*M|0|21!"
	"M|11|29*D|9|27*D|7|24*D|5|20*D|4|15*D|4|11*D|5|6*D|7|2*D|9|-1*D|11|-3*M|0|21!"
	"M|3|29*D|5|27*D|7|24*D|9|20*D|10|15*D|10|11*D|9|6*D|7|2*D|5|-1*D|3|-3*M|0|21!"
	"M|8|19*D|8|7*M|3|16*D|13|10*M|13|16*D|3|10*M|0|21!"
	"M|13|22*D|13|4*M|4|13*D|22|13*M|0|21!"
	"M|4|5*D|3|4*D|2|5*D|3|6*D|4|5*D|4|3*D|3|1*D|2|0*M|0|21!"
	"M|4|13*D|22|13*M|0|21!"
	"M|5|6*D|4|5*D|5|4*D|6|5*D|5|6*M|0|21!"
	"M|3|4*D|17|25*M|0|21!"
	"M|9|25*D|6|24*D|4|21*D|3|16*D|3|13*D|4|8*D|6|5*D|9|4*D|11|4*D|14|5*D|16|8*D|17|13*D|17|16*D|16|21*D|14|24*D|11|25*D|9|25*M|16|21*D|4|8*M|0|21!"
	"M|6|21*D|8|22*D|11|25*D|11|4*M|0|21!"
	"M|4|20*D|4|21*D|5|23*D|6|24*D|8|25*D|12|25*D|14|24*D|15|23*D|16|21*D|16|19*D|15|17*D|13|14*D|3|4*D|17|4*M|0|21!"
	"M|5|25*D|16|25*D|10|17*D|13|17*D|15|16*D|16|15*D|17|12*D|17|10*D|16|7*D|14|5*D|11|4*D|8|4*D|5|5*D|4|6*D|3|8*M|0|21!"
	"M|13|4*D|13|25*D|3|11*D|18|11*M|0|21!"
	"M|15|25*D|5|25*D|4|16*D|5|17*D|8|18*D|11|18*D|14|17*D|16|15*D|17|12*D|17|10*D|16|7*D|14|5*D|11|4*D|8|4*D|5|5*D|4|6*D|3|8*M|0|21!"
	"M|16|22*D|15|24*D|12|25*D|10|25*D|7|24*D|5|21*D|4|16*D|4|11*D|5|7*D|7|5*D|10|4*D|11|4*D|14|5*D|16|7*D|17|10*D|17|11*D|16|14*D|14|16*D|11|17*D|10|17*D|7|16*D|5|14*D|4|11*M|0|21!"
	"M|7|4*D|17|25*D|3|25*M|0|21!"
	"M|8|25*D|5|24*D|4|22*D|4|20*D|5|18*D|7|17*D|11|16*D|14|15*D|16|13*D|17|11*D|17|8*D|16|6*D|15|5*D|12|4*D|8|4*D|5|5*D|4|6*D|3|8*D|3|11*D|4|13*D|6|15*D|9|16*D|13|17*D|15|18*D|16|20*D|16|22*D|15|24*D|12|25*D|8|25*M|0|21!"
	"M|16|18*D|15|15*D|13|13*D|10|12*D|9|12*D|6|13*D|4|15*D|3|18*D|3|19*D|4|22*D|6|24*D|9|25*D|10|25*D|13|24*D|15|22*D|16|18*D|16|13*D|15|8*D|13|5*D|10|4*D|8|4*D|5|5*D|4|7*M|0|21!"
	"M|5|18*D|4|17*D|5|16*D|6|17*D|5|18*M|5|6*D|4|5*D|5|4*D|6|5*D|5|6*M|0|21!"
	"M|5|18*D|4|17*D|5|16*D|6|17*D|5|18*M|6|5*D|5|4*D|4|5*D|5|6*D|6|5*D|6|3*D|5|1*D|4|0*M|0|21!"
	"M|20|22*D|4|13*D|20|4*M|0|21!"
	"M|4|16*D|22|16*M|4|10*D|22|10*M|0|21!"
	"M|4|22*D|20|13*D|4|4*M|0|21!"
	"M|3|20*D|3|21*D|4|23*D|5|24*D|7|25*D|11|25*D|13|24*D|14|23*D|15|21*D|15|19*D|14|17*D|13|16*D|9|14*D|9|11*M|9|6*D|8|5*D|9|4*D|10|5*D|9|6*M|0|21!"
	"M|14|20*D|11|20*D|9|19*D|8|18*D|7|16*D|7|12*D|8|11*D|10|11*D|14|12*D|15|10*D|16|10*D|18|12*D|19|17*D|18|20*D|17|22*D|15|24*D|13|25*D|9|25*D|7|24*D|5|22*D|4|20*D|3|17*D|3|12*D|4|9*D|5|7*D|7|5*D|9|4*D|13|4*D|15|5*D|17|7*M|14|21*D|14|12*M|0|21!"
	"M|17|4*D|9|25*D|1|4*M|4|11*D|14|11*M|0|21!"
	"M|4|25*D|4|4*D|13|4*D|16|5*D|17|6*D|18|8*D|18|11*D|17|13*D|16|14*D|13|15*D|16|16*D|17|17*D|18|19*D|18|21*D|17|23*D|16|24*D|13|25*D|4|25*M|4|15*D|13|15*M|0|21!"
	"M|18|20*D|17|22*D|15|24*D|13|25*D|9|25*D|7|24*D|5|22*D|4|20*D|3|17*D|3|12*D|4|9*D|5|7*D|7|5*D|9|4*D|13|4*D|15|5*D|17|7*D|18|9*M|0|21!"
	"M|4|25*D|4|4*D|11|4*D|14|5*D|16|7*D|17|9*D|18|12*D|18|17*D|17|20*D|16|22*D|14|24*D|11|25*D|4|25*M|0|21!"
	"M|17|25*D|4|25*D|4|4*D|17|4*M|4|15*D|12|15*M|0|21!"
	"M|17|25*D|4|25*D|4|4*M|4|15*D|12|15*M|0|21!"
	"M|18|20*D|17|22*D|15|24*D|13|25*D|9|25*D|7|24*D|5|22*D|4|20*D|3|17*D|3|12*D|4|9*D|5|7*D|7|5*D|9|4*D|13|4*D|15|5*D|17|7*D|18|9*D|18|12*D|13|12*M|0|21!"
	"M|4|25*D|4|4*M|18|25*D|18|4*M|4|15*D|18|15*M|0|21!"
	"M|4|25*D|4|4*M|0|21!"
	"M|12|25*D|12|9*D|11|6*D|10|5*D|8|4*D|6|4*D|4|5*D|3|6*D|2|9*D|2|11*M|0|21!"
	"M|4|25*D|4|4*M|18|25*D|4|11*M|9|16*D|18|4*M|0|21!"
	"M|4|25*D|4|4*D|16|4*M|0|21!"
	"M|20|4*D|20|25*D|12|4*D|4|25*D|4|4*M|0|21!"
	"M|18|25*D|18|4*D|4|25*D|4|4*M|0|21!"
	"M|9|25*D|7|24*D|5|22*D|4|20*D|3|17*D|3|12*D|4|9*D|5|7*D|7|5*D|9|4*D|13|4*D|15|5*D|17|7*D|18|9*D|19|12*D|19|17*D|18|20*D|17|22*D|15|24*D|13|25*D|9|25*M|0|21!"
	"M|4|14*D|13|14*D|16|15*D|17|16*D|18|18*D|18|21*D|17|23*D|16|24*D|13|25*D|4|25*D|4|4*M|0|21!"
	"M|9|25*D|7|24*D|5|22*D|4|20*D|3|17*D|3|12*D|4|9*D|5|7*D|7|5*D|9|4*D|13|4*D|15|5*D|17|7*D|18|9*D|19|12*D|19|17*D|18|20*D|17|22*D|15|24*D|13|25*D|9|25*M|12|8*D|18|2*M|0|21!"
	"M|4|15*D|13|15*D|16|16*D|17|17*D|18|19*D|18|21*D|17|23*D|16|24*D|13|25*D|4|25*D|4|4*M|11|15*D|18|4*M|0|21!"
	"M|17|22*D|15|24*D|12|25*D|8|25*D|5|24*D|3|22*D|3|20*D|4|18*D|5|17*D|7|16*D|13|14*D|15|13*D|16|12*D|17|10*D|17|7*D|15|5*D|12|4*D|8|4*D|5|5*D|3|7*M|0|21!"
	"M|8|25*D|8|4*M|1|25*D|15|25*M|0|21!"
	"M|4|25*D|4|10*D|5|7*D|7|5*D|10|4*D|12|4*D|15|5*D|17|7*D|18|10*D|18|25*M|0|21!"
	"M|1|25*D|9|4*D|17|25*M|0|21!"
	"M|2|25*D|7|4*D|12|25*D|17|4*D|22|25*M|0|21!"
	"M|3|25*D|17|4*M|17|25*D|3|4*M|0|21!"
	"M|1|25*D|9|15*D|9|4*M|17|25*D|9|15*M|0|21!"
	"M|3|25*D|17|25*D|3|4*D|17|4*M|0|21!"
	"M|11|29*D|4|29*D|4|-3*D|11|-3*M|0|21!"
	"M|3|25*D|17|4*M|0|21!"
	"M|3|29*D|10|29*D|10|-3*D|3|-3*M|0|21!"
	"M|3|18*D|11|25*D|19|18*M|0|21!"
	"M|3|-3*D|22|-3*M|0|21!"
	"M|7|19*D|2|25*D|4|25*D|7|19*M|0|21!"
	"M|15|18*D|15|4*M|15|15*D|13|17*D|11|18*D|8|18*D|6|17*D|4|15*D|3|12*D|3|10*D|4|7*D|6|5*D|8|4*D|11|4*D|13|5*D|15|7*M|0|21!"
	"M|4|25*D|4|4*M|4|15*D|6|17*D|8|18*D|11|18*D|13|17*D|15|15*D|16|12*D|16|10*D|15|7*D|13|5*D|11|4*D|8|4*D|6|5*D|4|7*M|0|21!"
	"M|15|15*D|13|17*D|11|18*D|8|18*D|6|17*D|4|15*D|3|12*D|3|10*D|4|7*D|6|5*D|8|4*D|11|4*D|13|5*D|15|7*M|0|21!"
	"M|15|25*D|15|4*M|15|15*D|13|17*D|11|18*D|8|18*D|6|17*D|4|15*D|3|12*D|3|10*D|4|7*D|6|5*D|8|4*D|11|4*D|13|5*D|15|7*M|0|21!"
	"M|3|12*D|15|12*D|15|14*D|14|16*D|13|17*D|11|18*D|8|18*D|6|17*D|4|15*D|3|12*D|3|10*D|4|7*D|6|5*D|8|4*D|11|4*D|13|5*D|15|7*M|0|21!"
	"M|10|25*D|8|25*D|6|24*D|5|21*D|5|4*M|2|18*D|9|18*M|0|21!"
	"M|15|18*D|15|2*D|14|-1*D|13|-2*D|11|-3*D|8|-3*D|6|-2*M|15|15*D|13|17*D|11|18*D|8|18*D|6|17*D|4|15*D|3|12*D|3|10*D|4|7*D|6|5*D|8|4*D|11|4*D|13|5*D|15|7*M|0|21!"
	"M|4|25*D|4|4*M|4|14*D|7|17*D|9|18*D|12|18*D|14|17*D|15|14*D|15|4*M|0|21!"
	"M|3|25*D|4|24*D|5|25*D|4|26*D|3|25*M|4|18*D|4|4*M|0|21!"
	"M|5|25*D|6|24*D|7|25*D|6|26*D|5|25*M|6|18*D|6|1*D|5|-2*D|3|-3*D|1|-3*M|0|21!"
	"M|4|25*D|4|4*M|14|18*D|4|8*M|8|12*D|15|4*M|0|21!"
	"M|4|25*D|4|4*M|0|21!"
	"M|4|18*D|4|4*M|4|14*D|7|17*D|9|18*D|12|18*D|14|17*D|15|14*D|15|4*M|15|14*D|18|17*D|20|18*D|23|18*D|25|17*D|26|14*D|26|4*M|0|21!"
	"M|4|18*D|4|4*M|4|14*D|7|17*D|9|18*D|12|18*D|14|17*D|15|14*D|15|4*M|0|21!"
	"M|8|18*D|6|17*D|4|15*D|3|12*D|3|10*D|4|7*D|6|5*D|8|4*D|11|4*D|13|5*D|15|7*D|16|10*D|16|12*D|15|15*D|13|17*D|11|18*D|8|18*M|0|21!"
	"M|4|18*D|4|-3*M|4|15*D|6|17*D|8|18*D|11|18*D|13|17*D|15|15*D|16|12*D|16|10*D|15|7*D|13|5*D|11|4*D|8|4*D|6|5*D|4|7*M|0|21!"
	"M|15|18*D|15|-3*M|15|15*D|13|17*D|11|18*D|8|18*D|6|17*D|4|15*D|3|12*D|3|10*D|4|7*D|6|5*D|8|4*D|11|4*D|13|5*D|15|7*M|0|21!"
	"M|4|18*D|4|4*M|4|12*D|5|15*D|7|17*D|9|18*D|12|18*M|0|21!"
	"M|14|15*D|13|17*D|10|18*D|7|18*D|4|17*D|3|15*D|4|13*D|6|12*D|11|11*D|13|10*D|14|8*D|14|7*D|13|5*D|10|4*D|7|4*D|4|5*D|3|7*M|0|21!"
	"M|5|25*D|5|8*D|6|5*D|8|4*D|10|4*M|2|18*D|9|18*M|0|21!"
	"M|4|18*D|4|8*D|5|5*D|7|4*D|10|4*D|12|5*D|15|8*M|15|18*D|15|4*M|0|21!"
	"M|2|18*D|8|4*D|14|18*M|0|21!"
	"M|3|18*D|7|4*D|11|18*D|15|4*D|19|18*M|0|21!"
	"M|3|18*D|14|4*M|14|18*D|3|4*M|0|21!"
	"M|2|18*D|8|4*D|6|0*D|4|-2*D|2|-3*D|1|-3*M|14|18*D|8|4*M|0|21!"
	"M|3|18*D|14|18*D|3|4*D|14|4*M|0|21!"
	"M|9|29*D|7|28*D|6|27*D|5|25*D|5|23*D|6|21*D|7|20*D|8|18*D|8|16*D|6|14*D|4|13*D|6|12*D|8|10*D|8|8*D|7|6*D|6|5*D|5|3*D|5|1*D|6|-1*D|7|-2*D|9|-3*M|0|21!"
	"M|4|29*D|4|-3*M|0|21!"
	"M|5|29*D|7|28*D|8|27*D|9|25*D|9|23*D|8|21*D|7|20*D|6|18*D|6|16*D|8|14*D|10|13*D|8|12*D|6|10*D|6|8*D|7|6*D|8|5*D|9|3*D|9|1*D|8|-1*D|7|-2*D|5|-3*M|0|21!"
	"M|3|16*D|7|21*D|9|22*D|11|21*D|15|16*D|17|15*D|19|16*D|23|21*M|0|21!"
	"M|0|11*D|0|4*D|12|4*D|12|11*D|6|20*D|0|11*M|0|21!"
	"M|0|4!"
	"M|0|4!"
	"M|6|4!"
	"M|0|4!"
	"M|7|4!"
	"M|4|4!"
	"M|10|4!"
	"M|3|4!"
	"M|14|4!"
	"M|18|4!"
	"M|5|4!"
	"M|8|4!"
	"M|2|4!"
	"M|13|4!"
	"M|11|4!"
	"M|0|4!"
	"M|3|4!"
	"M|3|23*D|2|24*D|3|25*D|4|24*D|4|22*D|3|20*D|2|19*M|0|21!"
	"M|3|23*D|2|24*D|3|25*D|4|24*D|4|22*D|3|20*D|2|19*M|0|21!"
	"M|3|23*D|2|24*D|3|25*D|4|24*D|4|22*D|3|20*D|2|19*M|7|23*D|6|24*D|7|25*D|8|24*D|8|22*D|7|20*D|6|19*M|0|21!"
	"M|3|23*D|2|24*D|3|25*D|4|24*D|4|22*D|3|20*D|2|19*M|7|23*D|6|24*D|7|25*D|8|24*D|8|22*D|7|20*D|6|19*M|0|21!"
	"M|16|4!"
	"M|13|4!"
	"M|15|4!"
	"M|16|4!"
	"M|19|4!"
	"M|4|4!"
	"M|3|14*D|4|11*D|6|9*D|8|8*D|11|8*D|13|9*D|15|11*D|16|14*D|15|17*D|13|19*D|11|20*D|8|20*D|6|19*D|4|17*D|3|14*M|2|7*D|17|21*M|0|21!"
	"M|8|4!"
	"M|19|4!"
	"M|16|4!"
	"M|18|4!"
	"M|16|4!"
	"M|9|4!"
	"M|12|4!"
	"M|13|4!"
	"M|11|4!"
	"M|10|4!"
	"M|14|4!"
	"M|2|4!"
	"M|16|4*D|3|4*D|3|25*D|16|25*M|3|15*D|12|15*M|6|28*D|7|29*M|11|28*D|12|29*M|0|21!"
	"M|8|4!"
	"M|2|4!"
	"M|9|21*D|2|15*D|9|9*M|17|21*D|10|15*D|17|9*M|0|21!"
	"M|13|4!"
	"M|9|4!"
	"M|9|4!"
	"M|11|4!"
	"M|7|19*D|5|19*D|3|21*D|3|23*D|5|25*D|7|25*D|9|23*D|9|21*D|7|19*M|0|21!"
	"M|4|16*D|14|16*M|9|21*D|9|11*M|4|8*D|14|8*M|0|21!"
	"M|6|4!"
	"M|17|4!"
	"M|5|4!"
	"M|3|4!"
	"M|8|4!"
	"M|13|4!"
	"M|2|12*D|14|12*D|14|14*D|13|16*D|12|17*D|10|18*D|7|18*D|5|17*D|3|15*D|2|12*D|2|10*D|3|7*D|5|5*D|7|4*D|10|4*D|12|5*D|14|7*M|7|22*D|6|21*M|11|22*D|10|21*M|0|21!"
	"M|18|25*D|18|4*D|4|25*D|4|4*M|26|13*D|24|13*D|22|15*D|22|17*D|24|19*D|26|19*D|28|17*D|28|15*D|26|13*M|22|10*D|28|10*M|0|21!"
	"M|3|4!"
	"M|10|21*D|17|15*D|10|9*M|2|21*D|9|15*D|2|9*M|0|21!"
	"M|10|4!"
	"M|12|4!"
	"M|12|4!"
	"M|0|4!"
	"M|17|4*D|9|25*D|1|4*M|4|11*D|14|11*M|0|21!"
	"M|3|15*D|12|15*D|15|14*D|16|13*D|17|11*D|17|8*D|16|6*D|15|5*D|12|4*D|3|4*D|3|25*D|16|25*M|0|21!"
	"M|3|25*D|3|4*D|12|4*D|15|5*D|16|6*D|17|8*D|17|11*D|16|13*D|15|14*D|12|15*D|15|16*D|16|17*D|17|19*D|17|21*D|16|23*D|15|24*D|12|25*D|3|25*M|3|15*D|12|15*M|0|21!"
	"M|3|4*D|3|25*D|15|25*M|0|21!"
	"M|1|0*D|1|4*D|21|4*D|21|0*M|3|4*D|11|25*D|19|4*M|0|21!"
	"M|16|4*D|3|4*D|3|25*D|16|25*M|3|15*D|12|15*M|0|21!"
	"M|30|25*D|16|11*D|2|25*M|21|16*D|30|4*M|11|16*D|2|4*M|16|25*D|16|4*M|0|21!"
	"M|2|21*D|3|23*D|4|24*D|7|25*D|10|25*D|13|24*D|14|23*D|15|21*D|15|19*D|14|17*D|13|16*D|11|15*D|14|14*D|15|13*D|16|11*D|16|8*D|15|6*D|14|5*D|11|4*D|7|4*D|4|5*D|3|6*D|2|8*M|7|15*D|11|15*M|0|21!"
	"M|3|25*D|3|4*D|17|25*D|17|4*M|0|21!"
	"M|3|25*D|3|4*D|17|25*D|17|4*M|8|26*D|7|25*D|8|24*D|12|25*D|13|26*M|0|21!"
	"M|3|25*D|3|4*M|17|25*D|3|11*M|8|16*D|17|4*M|0|21!"
	"M|1|4*D|9|25*D|17|4*M|0|21!"
	"M|3|4*D|3|25*D|11|4*D|19|25*D|19|4*M|0|21!"
	"M|3|4*D|3|25*M|17|25*D|17|4*M|3|15*D|17|15*M|0|21!"
	"M|8|25*D|6|24*D|4|22*D|3|20*D|2|17*D|2|12*D|3|9*D|4|7*D|6|5*D|8|4*D|12|4*D|14|5*D|16|7*D|17|9*D|18|12*D|18|17*D|17|20*D|16|22*D|14|24*D|12|25*D|8|25*M|0|21!"
	"M|3|4*D|3|25*D|17|25*D|17|4*M|0|21!"
	"M|3|14*D|12|14*D|15|15*D|16|16*D|17|18*D|17|21*D|16|23*D|15|24*D|12|25*D|3|25*D|3|4*M|0|21!"
	"M|17|20*D|16|22*D|14|24*D|12|25*D|8|25*D|6|24*D|4|22*D|3|20*D|2|17*D|2|12*D|3|9*D|4|7*D|6|5*D|8|4*D|12|4*D|14|5*D|16|7*D|17|9*M|0|21!"
	"M|8|25*D|8|4*M|1|25*D|15|25*M|0|21!"
	"M|1|25*D|10|12*M|18|25*D|6|4*M|0|21!"
	"M|12|25*D|12|4*M|7|11*D|17|11*D|20|12*D|21|13*D|22|15*D|22|18*D|21|20*D|20|21*D|17|22*D|7|22*D|4|21*D|3|20*D|2|18*D|2|15*D|3|13*D|4|12*D|7|11*M|0|21!"
	"M|2|25*D|16|4*M|16|25*D|2|4*M|0|21!"
	"M|18|0*D|18|4*D|3|4*D|3|25*M|16|25*D|16|4*M|0|21!"
	"M|2|25*D|2|17*D|3|15*D|4|14*D|6|13*D|16|13*M|16|25*D|16|4*M|0|21!"
	"M|21|25*D|21|4*D|3|4*D|3|25*M|12|25*D|12|4*M|0|21!"
	"M|23|0*D|23|4*D|3|4*D|3|25*M|12|25*D|12|4*M|21|25*D|21|4*M|0|21!"
	"M|1|25*D|4|25*D|4|4*D|12|4*D|15|5*D|16|6*D|17|8*D|17|10*D|16|12*D|15|13*D|12|14*D|4|14*M|0|21!"
	"M|3|25*D|3|4*D|11|4*D|14|5*D|15|6*D|16|8*D|16|10*D|15|12*D|14|13*D|11|14*D|3|14*M|19|25*D|19|4*M|0|21!"
	"M|3|25*D|3|4*D|12|4*D|15|5*D|16|6*D|17|8*D|17|10*D|16|12*D|15|13*D|12|14*D|3|14*M|0|21!"
	"M|2|20*D|3|22*D|5|24*D|7|25*D|11|25*D|13|24*D|15|22*D|16|20*D|17|17*D|17|15*D|7|15*M|17|15*D|17|12*D|16|9*D|15|7*D|13|5*D|11|4*D|7|4*D|5|5*D|3|7*D|2|9*M|0|21!"
	"M|3|15*D|6|15*M|12|25*D|10|24*D|8|22*D|7|20*D|6|17*D|6|12*D|7|9*D|8|7*D|10|5*D|12|4*D|15|4*D|17|5*D|19|7*D|20|9*D|21|12*D|21|17*D|20|20*D|19|22*D|17|24*D|15|25*D|12|25*M|3|25*D|3|4*M|0|21!"
	"M|16|15*D|7|15*D|4|16*D|3|17*D|2|19*D|2|21*D|3|23*D|4|24*D|7|25*D|16|25*D|16|4*M|2|4*D|9|15*M|0|21!"
	"M|14|18*D|14|4*M|14|15*D|12|17*D|10|18*D|7|18*D|5|17*D|3|15*D|2|12*D|2|10*D|3|7*D|5|5*D|7|4*D|10|4*D|12|5*D|14|7*M|0|21!"
	"M|7|17*D|5|16*D|3|14*D|2|12*D|2|9*D|3|7*D|5|5*D|7|4*D|10|4*D|12|5*D|14|7*D|15|9*D|15|12*D|14|14*D|12|16*D|10|17*D|7|17*M|2|12*D|2|18*D|3|21*D|4|22*D|6|23*D|13|23*M|0|21!"
	"M|11|12*D|14|11*D|15|9*D|15|7*D|14|5*D|12|4*D|3|4*D|3|18*D|11|18*D|13|17*D|14|15*D|13|13*D|11|12*D|3|12*M|0|21!"
	"M|13|18*D|3|18*D|3|4*M|0|21!"
	"M|3|4*D|10|18*D|17|4*M|1|1*D|1|4*D|19|4*D|19|1*M|0|21!"
	"M|2|12*D|14|12*D|14|14*D|13|16*D|12|17*D|10|18*D|7|18*D|5|17*D|3|15*D|2|12*D|2|10*D|3|7*D|5|5*D|7|4*D|10|4*D|12|5*D|14|7*M|0|21!"
	"M|3|18*D|13|8*D|23|18*M|9|12*D|2|4*M|17|12*D|24|4*M|13|18*D|13|4*M|0|21!"
	"M|2|15*D|3|17*D|6|18*D|10|18*D|12|17*D|13|15*D|12|13*D|10|12*D|13|11*D|14|9*D|14|8*D|13|6*D|12|5*D|10|4*D|6|4*D|3|5*D|2|7*M|7|12*D|10|12*M|0|21!"
	"M|3|18*D|3|4*D|14|18*D|14|4*M|0|21!"
	"M|3|18*D|3|4*D|14|18*D|14|4*M|7|20*D|7|19*D|11|20*M|0|21!"
	"M|3|18*D|3|4*M|13|18*D|3|8*M|7|12*D|14|4*M|0|21!"
	"M|1|4*D|8|18*D|15|4*M|0|21!"
	"M|3|4*D|3|18*D|10|4*D|17|18*D|17|4*M|0|21!"
	"M|3|4*D|3|18*M|14|18*D|14|4*M|3|11*D|14|11*M|0|21!"
	"M|7|18*D|5|17*D|3|15*D|2|12*D|2|10*D|3|7*D|5|5*D|7|4*D|10|4*D|12|5*D|14|7*D|15|10*D|15|12*D|14|15*D|12|17*D|10|18*D|7|18*M|0|21!"
	"M|3|4*D|3|18*D|16|18*D|16|4*M|0|21!"
	"M|3|18*D|3|-3*M|3|15*D|5|17*D|7|18*D|10|18*D|12|17*D|14|15*D|15|12*D|15|10*D|14|7*D|12|5*D|10|4*D|7|4*D|5|5*D|3|7*M|0|21!"
	"M|14|15*D|12|17*D|10|18*D|7|18*D|5|17*D|3|15*D|2|12*D|2|10*D|3|7*D|5|5*D|7|4*D|10|4*D|12|5*D|14|7*M|0|21!"
	"M|7|18*D|7|4*M|1|18*D|13|18*M|0|21!"
	"M|1|18*D|7|4*D|5|0*D|3|-2*D|1|-3*D|0|-3*M|13|18*D|7|4*M|0|21!"
	"M|13|23*D|13|-3*M|13|15*D|11|17*D|9|18*D|7|18*D|5|17*D|3|15*D|2|12*D|2|10*D|3|7*D|5|5*D|7|4*D|9|4*D|11|5*D|13|7*D|15|5*D|17|4*D|19|4*D|21|5*D|23|7*D|24|10*D|24|12*D|23|15*D|21|17*D|19|18*D|17|18*D|15|17*D|13|15*M|0|21!"
	"M|2|18*D|13|4*M|13|18*D|2|4*M|0|21!"
	"M|3|18*D|3|4*D|18|4*D|18|1*M|16|18*D|16|4*M|0|21!"
	"M|2|18*D|2|14*D|3|12*D|5|11*D|12|12*M|12|18*D|12|4*M|0|21!"
	"M|3|18*D|3|4*D|25|4*D|25|18*M|14|18*D|14|4*M|0|21!"
	"M|3|18*D|3|4*D|27|4*D|27|1*M|14|18*D|14|4*M|25|18*D|25|4*M|0|21!"
	"M|1|18*D|4|18*D|4|4*D|11|4*D|14|5*D|15|7*D|15|9*D|14|11*D|11|12*D|4|12*M|0|21!"
	"M|3|18*D|3|4*D|10|4*D|13|5*D|14|7*D|14|9*D|13|11*D|10|12*D|3|12*M|17|18*D|17|4*M|0|21!"
	"M|3|18*D|3|4*D|10|4*D|13|5*D|14|7*D|14|9*D|13|11*D|10|12*D|3|12*M|0|21!"
	"M|2|15*D|4|17*D|7|18*D|10|18*D|12|17*D|14|15*D|15|12*D|15|11*D|8|11*M|15|11*D|15|10*D|14|7*D|12|5*D|10|4*D|7|4*D|4|5*D|2|7*M|0|21!"
	"M|3|4*D|3|18*M|3|11*D|6|11*M|11|18*D|9|17*D|7|15*D|6|12*D|6|10*D|7|7*D|9|5*D|11|4*D|14|4*D|16|5*D|18|7*D|19|10*D|19|12*D|18|15*D|16|17*D|14|18*D|11|18*M|0|21!"
	"M|13|12*D|5|12*D|3|13*D|2|15*D|3|17*D|5|18*D|13|18*D|13|4*M|8|12*D|2|4*M|0|21";
