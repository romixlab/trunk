int firstChar_1 = 32;
int capital_1 =  21, baseline_1 = 0, bottom_1 = 0;

string widths_1 = "18,7,12,20,18,22,23,6,11,11,14,22,6,22,6,25,18,16,18,18,19,18,18,18,18,18,6,6,20,22,20,16,25,21,21,19,21,20,20,22,24,11,14,23,19,25,23,20,21,20,22,18,19,24,21,25,22,22,18,11,27,11,20,21,6,19,20,17,20,17,13,18,22,11,8,21,11,33,22,18,20,20,17,15,15,22,19,25,20,19,16,9,4,9,22,16,0,0,6,0,7,4,10,3,14,18,5,8,2,13,11,0,3,6,6,14,14,16,13,15,16,19,4,17,8,19,16,18,16,9,12,13,11,10,14,2,20,8,2,19,13,9,9,11,14,17,6,17,5,3,8,13,17,35,3,19,10,12,12,0,21,21,21,19,23,20,35,19,24,24,23,23,25,24,20,25,21,19,18,23,29,22,25,23,35,35,24,30,21,19,29,22,19,18,19,18,20,17,31,16,22,22,21,20,23,21,18,23,20,17,18,19,29,20,23,21,31,31,21,26,18,17,26,18";

string draw_1 = "M|18|4!"
	"M|4|25*D|3|23*D|4|11*D|5|23*D|4|25*M|4|23*D|4|17*M|4|6*D|3|5*D|4|4*D|5|5*D|4|6*M|0|21!"
	"M|3|25*D|2|18*D|4|25*M|9|25*D|8|18*D|10|25*M|0|21!"
	"M|11|25*D|4|-3*M|17|25*D|10|-3*M|4|14*D|18|14*M|3|8*D|17|8*M|0|21!"
	"M|7|29*D|7|0*M|11|29*D|11|0*M|15|22*D|14|21*D|15|20*D|16|21*D|16|22*D|14|24*D|11|25*D|7|25*D|4|24*D|2|22*D|2|20*D|3|18*D|4|17*D|6|16*D|12|14*D|14|13*D|16|11*D|16|7*D|14|5*D|11|4*D|7|4*D|4|5*D|2|7*D|2|8*D|3|9*D|4|8*D|3|7*M|2|20*D|4|18*D|6|17*D|12|15*D|14|14*D|15|13*D|16|11*M|0|21!"
	"M|7|25*D|5|25*D|3|24*D|2|22*D|2|20*D|4|18*D|6|18*D|8|19*D|9|21*D|9|23*D|7|25*D|9|24*D|12|23*D|15|23*D|18|24*D|20|25*D|2|4*M|16|11*D|14|10*D|13|8*D|13|6*D|15|4*D|17|4*D|19|5*D|20|7*D|20|9*D|18|11*D|16|11*M|14|10*D|14|5*M|19|10*D|19|5*M|3|19*D|3|24*M|8|19*D|8|24*M|0|21!"
	"M|20|17*D|19|16*D|20|15*D|21|16*D|21|17*D|20|18*D|19|18*D|18|17*D|17|15*D|15|10*D|13|7*D|11|5*D|9|4*D|6|4*D|3|5*D|2|7*D|2|10*D|3|12*D|9|16*D|11|18*D|12|20*D|12|22*D|11|24*D|9|25*D|7|24*D|6|22*D|6|20*D|7|17*D|9|14*D|14|7*D|16|5*D|19|4*D|20|4*D|21|5*D|21|6*M|6|4*D|4|5*D|3|7*D|3|10*D|4|12*D|6|14*M|6|20*D|7|18*D|15|7*D|17|5*D|19|4*M|0|21!"
	"M|3|25*D|2|18*D|4|25*M|0|21!"
	"M|9|29*D|7|27*D|5|24*D|3|20*D|2|15*D|2|11*D|3|6*D|5|2*D|7|-1*D|9|-3*M|7|27*D|5|23*D|4|20*D|3|15*D|3|11*D|4|6*D|5|3*D|7|-1*M|0|21!"
	"M|2|29*D|4|27*D|6|24*D|8|20*D|9|15*D|9|11*D|8|6*D|6|2*D|4|-1*D|2|-3*M|4|27*D|6|23*D|7|20*D|8|15*D|8|11*D|7|6*D|6|3*D|4|-1*M|0|21!"
	"M|7|16*D|7|4*M|2|13*D|12|7*M|12|13*D|2|7*M|0|21!"
	"M|11|22*D|11|4*M|2|13*D|20|13*M|0|21!"
	"M|3|4*D|2|5*D|3|6*D|4|5*D|4|3*D|3|1*D|2|0*M|0|21!"
	"M|2|13*D|20|13*M|0|21!"
	"M|3|6*D|2|5*D|3|4*D|4|5*D|3|6*M|0|21!"
	"M|2|4*D|23|25*M|24|25*D|3|4*M|0|21!"
	"M|8|25*D|5|24*D|3|21*D|2|16*D|2|13*D|3|8*D|5|5*D|8|4*D|10|4*D|13|5*D|15|8*D|16|13*D|16|16*D|15|21*D|13|24*D|10|25*D|8|25*D|6|24*D|5|23*D|4|21*D|3|16*D|3|13*D|4|8*D|5|6*D|6|5*D|8|4*M|10|4*D|12|5*D|13|6*D|14|8*D|15|13*D|15|16*D|14|21*D|13|23*D|12|24*D|10|25*M|0|21!"
	"M|5|21*D|7|22*D|10|25*D|10|4*M|9|24*D|9|4*M|5|4*D|14|4*M|0|21!"
	"M|3|21*D|4|20*D|3|19*D|2|20*D|2|21*D|3|23*D|4|24*D|7|25*D|11|25*D|14|24*D|15|23*D|16|21*D|16|19*D|15|17*D|12|15*D|7|13*D|5|12*D|3|10*D|2|7*D|2|4*M|11|25*D|13|24*D|14|23*D|15|21*D|15|19*D|14|17*D|11|15*D|7|13*M|2|6*D|3|7*D|5|7*D|10|5*D|13|5*D|15|6*D|16|7*D|16|9*M|5|7*D|10|4*D|14|4*D|15|5*D|16|7*M|0|21!"
	"M|3|21*D|4|20*D|3|19*D|2|20*D|2|21*D|3|23*D|4|24*D|7|25*D|11|25*D|14|24*D|15|22*D|15|19*D|14|17*D|11|16*D|8|16*M|11|25*D|13|24*D|14|22*D|14|19*D|13|17*D|11|16*D|13|15*D|15|13*D|16|11*D|16|8*D|15|6*D|14|5*D|11|4*D|7|4*D|4|5*D|3|6*D|2|8*D|2|9*D|3|10*D|4|9*D|3|8*M|14|14*D|15|11*D|15|8*D|14|6*D|13|5*D|11|4*M|0|21!"
	"M|11|23*D|11|4*M|17|10*D|1|10*D|12|25*D|12|4*M|8|4*D|15|4*M|0|21!"
	"M|4|24*D|9|24*D|14|25*D|4|25*D|2|15*D|4|17*D|7|18*D|10|18*D|13|17*D|15|15*D|16|12*D|16|10*D|15|7*D|13|5*D|10|4*D|7|4*D|4|5*D|3|6*D|2|8*D|2|9*D|3|10*D|4|9*D|3|8*M|10|18*D|12|17*D|14|15*D|15|12*D|15|10*D|14|7*D|12|5*D|10|4*M|0|21!"
	"M|14|22*D|13|21*D|14|20*D|15|21*D|15|22*D|14|24*D|12|25*D|9|25*D|6|24*D|4|22*D|3|20*D|2|16*D|2|10*D|3|7*D|5|5*D|8|4*D|10|4*D|13|5*D|15|7*D|16|10*D|16|11*D|15|14*D|13|16*D|10|17*D|9|17*D|6|16*D|4|14*D|3|11*M|9|25*D|7|24*D|5|22*D|4|20*D|3|16*D|3|10*D|4|7*D|6|5*D|8|4*M|10|4*D|12|5*D|14|7*D|15|10*D|15|11*D|14|14*D|12|16*D|10|17*M|0|21!"
	"M|2|25*D|2|19*M|2|21*D|3|23*D|5|25*D|7|25*D|12|22*D|14|22*D|15|23*D|16|25*D|16|22*D|15|19*D|11|14*D|10|12*D|9|9*D|9|4*M|3|23*D|5|24*D|7|24*D|12|22*M|15|19*D|10|14*D|9|12*D|8|9*D|8|4*M|0|21!"
	"M|7|25*D|4|24*D|3|22*D|3|19*D|4|17*D|7|16*D|11|16*D|14|17*D|15|19*D|15|22*D|14|24*D|11|25*D|7|25*D|5|24*D|4|22*D|4|19*D|5|17*D|7|16*D|4|15*D|3|14*D|2|12*D|2|8*D|3|6*D|4|5*D|7|4*D|11|4*D|14|5*D|15|6*D|16|8*D|16|12*D|15|14*D|14|15*D|11|16*D|13|17*D|14|19*D|14|22*D|13|24*D|11|25*M|7|16*D|5|15*D|4|14*D|3|12*D|3|8*D|4|6*D|5|5*D|7|4*M|11|4*D|13|5*D|14|6*D|15|8*D|15|12*D|14|14*D|13|15*D|11|16*M|0|21!"
	"M|15|18*D|14|15*D|12|13*D|9|12*D|8|12*D|5|13*D|3|15*D|2|18*D|2|19*D|3|22*D|5|24*D|8|25*D|10|25*D|13|24*D|15|22*D|16|19*D|16|13*D|15|9*D|14|7*D|12|5*D|9|4*D|6|4*D|4|5*D|3|7*D|3|8*D|4|9*D|5|8*D|4|7*M|8|12*D|6|13*D|4|15*D|3|18*D|3|19*D|4|22*D|6|24*D|8|25*M|10|25*D|12|24*D|14|22*D|15|19*D|15|13*D|14|9*D|13|7*D|11|5*D|9|4*M|0|21!"
	"M|3|18*D|2|17*D|3|16*D|4|17*D|3|18*M|3|6*D|2|5*D|3|4*D|4|5*D|3|6*M|0|21!"
	"M|3|18*D|2|17*D|3|16*D|4|17*D|3|18*M|3|4*D|2|5*D|3|6*D|4|5*D|4|3*D|3|1*D|2|0*M|0|21!"
	"M|18|22*D|2|13*D|18|4*M|15|20*D|4|13*D|15|6*M|0|21!"
	"M|2|16*D|20|16*M|2|10*D|20|10*M|0|21!"
	"M|2|22*D|18|13*D|2|4*M|5|20*D|16|13*D|5|6*M|0|21!"
	"M|3|21*D|4|20*D|3|19*D|2|20*D|2|21*D|3|23*D|4|24*D|6|25*D|9|25*D|12|24*D|13|23*D|14|21*D|14|19*D|13|17*D|12|16*D|8|14*D|8|11*M|9|25*D|11|24*D|12|23*D|13|21*D|13|19*D|12|17*D|10|15*M|8|6*D|7|5*D|8|4*D|9|5*D|8|6*M|0|21!"
	"M|17|17*D|16|19*D|14|20*D|11|20*D|9|19*D|8|18*D|7|15*D|7|12*D|8|10*D|10|9*D|13|9*D|15|10*D|16|12*D|16|10*D|18|9*D|20|9*D|22|11*D|23|14*D|23|16*D|22|19*D|21|21*D|19|23*D|17|24*D|14|25*D|11|25*D|8|24*D|6|23*D|4|21*D|3|19*D|2|16*D|2|13*D|3|10*D|4|8*D|6|6*D|8|5*D|11|4*D|14|4*D|17|5*D|19|6*D|20|7*M|11|20*D|9|18*D|8|15*D|8|12*D|9|10*D|10|9*M|17|20*D|16|12*M|18|20*D|17|12*D|17|10*D|18|9*M|0|21!"
	"M|17|4*D|10|25*D|3|4*M|10|22*D|16|4*M|5|10*D|14|10*M|1|4*D|7|4*M|13|4*D|19|4*M|0|21!"
	"M|5|25*D|5|4*M|6|25*D|6|4*M|2|25*D|14|25*D|17|24*D|18|23*D|19|21*D|19|19*D|18|17*D|17|16*D|14|15*D|17|14*D|18|13*D|19|11*D|19|8*D|18|6*D|17|5*D|14|4*D|2|4*M|14|25*D|16|24*D|17|23*D|18|21*D|18|19*D|17|17*D|16|16*D|14|15*D|16|14*D|17|13*D|18|11*D|18|8*D|17|6*D|16|5*D|14|4*M|6|15*D|14|15*M|0|21!"
	"M|16|22*D|17|19*D|17|25*D|16|22*D|14|24*D|11|25*D|9|25*D|6|24*D|4|22*D|3|20*D|2|17*D|2|12*D|3|9*D|4|7*D|6|5*D|9|4*D|11|4*D|14|5*D|16|7*D|17|9*M|9|25*D|7|24*D|5|22*D|4|20*D|3|17*D|3|12*D|4|9*D|5|7*D|7|5*D|9|4*M|0|21!"
	"M|5|25*D|5|4*M|6|25*D|6|4*M|2|25*D|12|25*D|15|24*D|17|22*D|18|20*D|19|17*D|19|12*D|18|9*D|17|7*D|15|5*D|12|4*D|2|4*M|12|25*D|14|24*D|16|22*D|17|20*D|18|17*D|18|12*D|17|9*D|16|7*D|14|5*D|12|4*M|0|21!"
	"M|5|25*D|5|4*M|6|25*D|6|4*M|12|19*D|12|11*M|2|25*D|18|25*D|18|19*D|17|25*M|6|15*D|12|15*M|2|4*D|18|4*D|18|10*D|17|4*M|0|21!"
	"M|5|25*D|5|4*M|6|25*D|6|4*M|12|19*D|12|11*M|2|25*D|18|25*D|18|19*D|17|25*M|6|15*D|12|15*M|2|4*D|9|4*M|0|21!"
	"M|16|22*D|17|19*D|17|25*D|16|22*D|14|24*D|11|25*D|9|25*D|6|24*D|4|22*D|3|20*D|2|17*D|2|12*D|3|9*D|4|7*D|6|5*D|9|4*D|11|4*D|14|5*D|16|7*M|9|25*D|7|24*D|5|22*D|4|20*D|3|17*D|3|12*D|4|9*D|5|7*D|7|5*D|9|4*M|16|12*D|16|4*M|17|12*D|17|4*M|13|12*D|20|12*M|0|21!"
	"M|5|25*D|5|4*M|6|25*D|6|4*M|18|25*D|18|4*M|19|25*D|19|4*M|2|25*D|9|25*M|15|25*D|22|25*M|6|15*D|18|15*M|2|4*D|9|4*M|15|4*D|22|4*M|0|21!"
	"M|5|25*D|5|4*M|6|25*D|6|4*M|2|25*D|9|25*M|2|4*D|9|4*M|0|21!"
	"M|9|25*D|9|8*D|8|5*D|6|4*D|4|4*D|2|5*D|1|7*D|1|9*D|2|10*D|3|9*D|2|8*M|8|25*D|8|8*D|7|5*D|6|4*M|5|25*D|12|25*M|0|21!"
	"M|5|25*D|5|4*M|6|25*D|6|4*M|19|25*D|6|12*M|11|16*D|19|4*M|10|16*D|18|4*M|2|25*D|9|25*M|15|25*D|21|25*M|2|4*D|9|4*M|15|4*D|21|4*M|0|21!"
	"M|5|25*D|5|4*M|6|25*D|6|4*M|2|25*D|9|25*M|2|4*D|17|4*D|17|10*D|16|4*M|0|21!"
	"M|19|4*D|19|25*D|12|4*D|5|25*D|5|4*M|2|25*D|6|25*D|12|7*M|20|25*D|20|4*M|19|25*D|23|25*M|2|4*D|8|4*M|16|4*D|23|4*M|0|21!"
	"M|5|25*D|5|4*M|2|25*D|6|25*D|18|6*M|6|23*D|18|4*D|18|25*M|15|25*D|21|25*M|2|4*D|8|4*M|0|21!"
	"M|9|25*D|6|24*D|4|22*D|3|20*D|2|16*D|2|13*D|3|9*D|4|7*D|6|5*D|9|4*D|11|4*D|14|5*D|16|7*D|17|9*D|18|13*D|18|16*D|17|20*D|16|22*D|14|24*D|11|25*D|9|25*D|7|24*D|5|22*D|4|20*D|3|16*D|3|13*D|4|9*D|5|7*D|7|5*D|9|4*M|11|4*D|13|5*D|15|7*D|16|9*D|17|13*D|17|16*D|16|20*D|15|22*D|13|24*D|11|25*M|0|21!"
	"M|5|25*D|5|4*M|6|25*D|6|4*M|2|25*D|14|25*D|17|24*D|18|23*D|19|21*D|19|18*D|18|16*D|17|15*D|14|14*D|6|14*M|14|25*D|16|24*D|17|23*D|18|21*D|18|18*D|17|16*D|16|15*D|14|14*M|2|4*D|9|4*M|0|21!"
	"M|9|25*D|6|24*D|4|22*D|3|20*D|2|16*D|2|13*D|3|9*D|4|7*D|6|5*D|9|4*D|11|4*D|14|5*D|16|7*D|17|9*D|18|13*D|18|16*D|17|20*D|16|22*D|14|24*D|11|25*D|9|25*D|7|24*D|5|22*D|4|20*D|3|16*D|3|13*D|4|9*D|5|7*D|7|5*D|9|4*M|11|4*D|13|5*D|15|7*D|16|9*D|17|13*D|17|16*D|16|20*D|15|22*D|13|24*D|11|25*M|6|6*D|6|7*D|7|9*D|9|10*D|10|10*D|12|9*D|13|7*D|14|0*D|15|-1*D|17|-1*D|18|1*D|18|2*M|13|7*D|14|3*D|15|1*D|16|0*D|17|0*D|18|1*M|0|21!"
	"M|5|25*D|5|4*M|6|25*D|6|4*M|2|25*D|14|25*D|17|24*D|18|23*D|19|21*D|19|19*D|18|17*D|17|16*D|14|15*D|6|15*M|14|25*D|16|24*D|17|23*D|18|21*D|18|19*D|17|17*D|16|16*D|14|15*M|2|4*D|9|4*M|11|15*D|13|14*D|14|13*D|17|6*D|18|5*D|19|5*D|20|6*D|20|7*M|13|14*D|14|12*D|16|5*D|17|4*D|19|4*D|20|6*M|0|21!"
	"M|15|22*D|16|25*D|16|19*D|15|22*D|13|24*D|10|25*D|7|25*D|4|24*D|2|22*D|2|20*D|3|18*D|4|17*D|6|16*D|12|14*D|14|13*D|16|11*D|16|7*D|14|5*D|11|4*D|8|4*D|5|5*D|3|7*D|2|10*D|2|4*D|3|7*M|2|20*D|4|18*D|6|17*D|12|15*D|14|14*D|15|13*D|16|11*M|0|21!"
	"M|9|25*D|9|4*M|10|25*D|10|4*M|3|25*D|2|19*D|2|25*D|17|25*D|17|19*D|16|25*M|6|4*D|13|4*M|0|21!"
	"M|5|25*D|5|10*D|6|7*D|8|5*D|11|4*D|13|4*D|16|5*D|18|7*D|19|10*D|19|25*M|6|25*D|6|10*D|7|7*D|9|5*D|11|4*M|2|25*D|9|25*M|16|25*D|22|25*M|0|21!"
	"M|3|25*D|10|4*D|17|25*M|4|25*D|10|7*M|1|25*D|7|25*M|13|25*D|19|25*M|0|21!"
	"M|4|25*D|8|4*D|12|25*D|16|4*D|20|25*M|5|25*D|8|9*M|13|25*D|16|9*M|1|25*D|8|25*M|17|25*D|23|25*M|0|21!"
	"M|4|25*D|17|4*M|5|25*D|18|4*M|18|25*D|4|4*M|2|25*D|8|25*M|14|25*D|20|25*M|2|4*D|8|4*M|14|4*D|20|4*M|0|21!"
	"M|3|25*D|10|14*D|10|4*M|4|25*D|11|14*D|11|4*M|18|25*D|11|14*M|1|25*D|7|25*M|14|25*D|20|25*M|7|4*D|14|4*M|0|21!"
	"M|15|25*D|2|4*D|16|4*D|16|10*D|15|4*M|3|25*D|2|19*D|2|25*D|16|25*D|3|4*M|0|21!"
	"M|9|29*D|2|29*D|2|-3*D|9|-3*M|3|29*D|3|-3*M|0|21!"
	"M|25|4*D|4|25*M|3|25*D|24|4*M|0|21!"
	"M|8|29*D|8|-3*M|2|29*D|9|29*D|9|-3*D|2|-3*M|0|21!"
	"M|2|20*D|10|25*D|18|20*D|10|24*D|2|20*M|0|21!"
	"M|2|-3*D|19|-3*M|0|21!"
	"M|2|25*D|3|24*D|4|22*D|4|20*D|3|19*D|2|20*D|3|21*M|0|21!"
	"M|4|16*D|4|15*D|3|15*D|3|16*D|4|17*D|6|18*D|10|18*D|12|17*D|13|16*D|14|14*D|14|7*D|15|5*D|16|4*D|17|4*M|13|16*D|13|7*D|14|5*D|16|4*M|13|14*D|12|13*D|6|12*D|3|11*D|2|9*D|2|7*D|3|5*D|6|4*D|9|4*D|11|5*D|13|7*M|6|12*D|4|11*D|3|9*D|3|7*D|4|5*D|6|4*M|0|21!"
	"M|5|25*D|5|4*M|2|25*D|6|25*D|6|4*M|6|15*D|8|17*D|10|18*D|12|18*D|15|17*D|17|15*D|18|12*D|18|10*D|17|7*D|15|5*D|12|4*D|10|4*D|8|5*D|6|7*M|12|18*D|14|17*D|16|15*D|17|12*D|17|10*D|16|7*D|14|5*D|12|4*M|0|21!"
	"M|14|15*D|13|14*D|14|13*D|15|14*D|15|15*D|13|17*D|11|18*D|8|18*D|5|17*D|3|15*D|2|12*D|2|10*D|3|7*D|5|5*D|8|4*D|10|4*D|13|5*D|15|7*M|8|18*D|6|17*D|4|15*D|3|12*D|3|10*D|4|7*D|6|5*D|8|4*M|0|21!"
	"M|14|25*D|14|4*D|18|4*M|11|25*D|15|25*D|15|4*M|14|15*D|12|17*D|10|18*D|8|18*D|5|17*D|3|15*D|2|12*D|2|10*D|3|7*D|5|5*D|8|4*D|10|4*D|12|5*D|14|7*M|8|18*D|6|17*D|4|15*D|3|12*D|3|10*D|4|7*D|6|5*D|8|4*M|0|21!"
	"M|8|4*D|6|5*D|4|7*D|3|10*D|3|12*D|15|12*D|15|14*D|14|16*D|13|17*D|11|18*D|8|18*D|5|17*D|3|15*D|2|12*D|2|10*D|3|7*D|5|5*D|8|4*D|10|4*D|13|5*D|15|7*M|14|12*D|14|15*D|13|17*M|8|18*D|6|17*D|4|15*D|3|12*M|0|21!"
	"M|10|24*D|9|23*D|10|22*D|11|23*D|11|24*D|10|25*D|8|25*D|6|24*D|5|22*D|5|4*M|8|25*D|7|24*D|6|22*D|6|4*M|2|18*D|10|18*M|2|4*D|9|4*M|0|21!"
	"M|8|18*D|6|17*D|5|16*D|4|14*D|4|12*D|5|10*D|6|9*D|8|8*D|10|8*D|12|9*D|13|10*D|14|12*D|14|14*D|13|16*D|12|17*D|10|18*D|8|18*M|6|17*D|5|15*D|5|11*D|6|9*M|12|9*D|13|11*D|13|15*D|12|17*M|13|16*D|14|17*D|16|18*D|16|17*D|14|17*M|5|10*D|4|9*D|3|7*D|3|6*D|4|4*D|7|3*D|12|3*D|15|2*D|16|1*D|16|0*D|15|-2*D|12|-3*D|6|-3*D|3|-2*D|2|0*D|2|1*D|3|3*D|6|4*M|3|6*D|4|5*D|7|4*D|12|4*D|15|3*D|16|1*M|0|21!"
	"M|5|25*D|5|4*M|2|25*D|6|25*D|6|4*M|6|15*D|8|17*D|11|18*D|13|18*D|16|17*D|17|15*D|17|4*M|13|18*D|15|17*D|16|15*D|16|4*M|2|4*D|9|4*M|13|4*D|20|4*M|0|21!"
	"M|5|25*D|4|24*D|5|23*D|6|24*D|5|25*M|5|18*D|5|4*M|2|18*D|6|18*D|6|4*M|2|4*D|9|4*M|0|21!"
	"M|5|25*D|4|24*D|5|23*D|6|24*D|5|25*M|2|18*D|6|18*D|6|0*D|5|-2*D|3|-3*D|1|-3*D|0|-2*D|0|-1*D|1|0*D|2|-1*D|1|-2*M|5|18*D|5|0*D|4|-2*D|3|-3*M|0|21!"
	"M|5|25*D|5|4*M|2|25*D|6|25*D|6|4*M|16|18*D|6|8*M|11|12*D|17|4*M|10|12*D|16|4*M|13|18*D|19|18*M|2|4*D|9|4*M|13|4*D|19|4*M|0|21!"
	"M|5|25*D|5|4*M|2|25*D|6|25*D|6|4*M|2|4*D|9|4*M|0|21!"
	"M|5|18*D|5|4*M|2|18*D|6|18*D|6|4*M|6|15*D|8|17*D|11|18*D|13|18*D|16|17*D|17|15*D|17|4*M|13|18*D|15|17*D|16|15*D|16|4*M|17|15*D|19|17*D|22|18*D|24|18*D|27|17*D|28|15*D|28|4*M|24|18*D|26|17*D|27|15*D|27|4*M|2|4*D|9|4*M|13|4*D|20|4*M|24|4*D|31|4*M|0|21!"
	"M|5|18*D|5|4*M|2|18*D|6|18*D|6|4*M|6|15*D|8|17*D|11|18*D|13|18*D|16|17*D|17|15*D|17|4*M|13|18*D|15|17*D|16|15*D|16|4*M|2|4*D|9|4*M|13|4*D|20|4*M|0|21!"
	"M|8|18*D|5|17*D|3|15*D|2|12*D|2|10*D|3|7*D|5|5*D|8|4*D|10|4*D|13|5*D|15|7*D|16|10*D|16|12*D|15|15*D|13|17*D|10|18*D|8|18*D|6|17*D|4|15*D|3|12*D|3|10*D|4|7*D|6|5*D|8|4*M|10|4*D|12|5*D|14|7*D|15|10*D|15|12*D|14|15*D|12|17*D|10|18*M|0|21!"
	"M|5|18*D|5|-3*M|2|18*D|6|18*D|6|-3*M|6|15*D|8|17*D|10|18*D|12|18*D|15|17*D|17|15*D|18|12*D|18|10*D|17|7*D|15|5*D|12|4*D|10|4*D|8|5*D|6|7*M|12|18*D|14|17*D|16|15*D|17|12*D|17|10*D|16|7*D|14|5*D|12|4*M|2|-3*D|9|-3*M|0|21!"
	"M|14|18*D|14|-3*M|15|18*D|15|-3*M|14|15*D|12|17*D|10|18*D|8|18*D|5|17*D|3|15*D|2|12*D|2|10*D|3|7*D|5|5*D|8|4*D|10|4*D|12|5*D|14|7*M|8|18*D|6|17*D|4|15*D|3|12*D|3|10*D|4|7*D|6|5*D|8|4*M|11|-3*D|18|-3*M|0|21!"
	"M|5|18*D|5|4*M|2|18*D|6|18*D|6|4*M|6|12*D|7|15*D|9|17*D|11|18*D|14|18*D|15|17*D|15|16*D|14|15*D|13|16*D|14|17*M|2|4*D|9|4*M|0|21!"
	"M|12|16*D|13|18*D|13|14*D|12|16*D|11|17*D|9|18*D|5|18*D|3|17*D|2|16*D|2|14*D|3|13*D|5|12*D|10|10*D|12|9*D|13|8*M|2|15*D|3|14*D|5|13*D|10|11*D|12|10*D|13|9*D|13|6*D|12|5*D|10|4*D|6|4*D|4|5*D|3|6*D|2|8*D|2|4*D|3|6*M|0|21!"
	"M|8|4*D|7|5*D|6|8*D|6|25*D|5|25*D|5|8*D|6|5*D|8|4*D|10|4*D|12|5*D|13|7*M|2|18*D|10|18*M|0|21!"
	"M|5|18*D|5|7*D|6|5*D|9|4*D|11|4*D|14|5*D|16|7*M|2|18*D|6|18*D|6|7*D|7|5*D|9|4*M|16|18*D|16|4*D|20|4*M|13|18*D|17|18*D|17|4*M|0|21!"
	"M|3|18*D|9|4*D|15|18*M|4|18*D|9|6*M|1|18*D|7|18*M|11|18*D|17|18*M|0|21!"
	"M|4|18*D|8|4*D|12|18*D|16|4*D|20|18*M|5|18*D|8|7*M|13|18*D|16|7*M|1|18*D|8|18*M|17|18*D|23|18*M|0|21!"
	"M|4|18*D|15|4*M|5|18*D|16|4*M|16|18*D|4|4*M|2|18*D|8|18*M|12|18*D|18|18*M|2|4*D|8|4*M|12|4*D|18|4*M|0|21!"
	"M|3|18*D|9|4*D|7|0*D|5|-2*D|3|-3*D|2|-3*D|1|-2*D|2|-1*D|3|-2*M|4|18*D|9|6*M|15|18*D|9|4*M|1|18*D|7|18*M|11|18*D|17|18*M|0|21!"
	"M|13|18*D|2|4*D|14|4*D|14|8*D|13|4*M|3|18*D|2|14*D|2|18*D|14|18*D|3|4*M|0|21!"
	"M|7|29*D|5|28*D|4|27*D|3|25*D|3|23*D|4|21*D|5|20*D|6|18*D|6|16*D|4|14*M|5|28*D|4|26*D|4|24*D|5|22*D|6|21*D|7|19*D|7|17*D|6|15*D|2|13*D|6|11*D|7|9*D|7|7*D|6|5*D|5|4*D|4|2*D|4|0*D|5|-2*D|7|-3*M|4|12*D|6|10*D|6|8*D|5|6*D|4|5*D|3|3*D|3|1*D|4|-1*D|5|-2*M|0|21!"
	"M|2|29*D|2|-2*M|0|21!"
	"M|2|29*D|4|28*D|5|27*D|6|25*D|6|23*D|5|21*D|4|20*D|3|18*D|3|16*D|5|14*M|4|28*D|5|26*D|5|24*D|4|22*D|3|21*D|2|19*D|2|17*D|3|15*D|7|13*D|3|11*D|2|9*D|2|7*D|3|5*D|4|4*D|5|2*D|5|0*D|4|-2*D|2|-3*M|5|12*D|3|10*D|3|8*D|4|6*D|5|5*D|6|3*D|6|1*D|5|-1*D|4|-2*M|0|21!"
	"M|2|17*D|2|19*D|3|22*D|5|23*D|7|23*D|9|22*D|13|19*D|15|18*D|17|18*D|19|19*D|20|21*D|20|23*M|2|19*D|3|21*D|5|22*D|7|22*D|9|21*D|13|18*D|15|17*D|17|17*D|19|18*D|20|21*M|0|21!"
	"M|14|4*D|14|12*D|8|21*D|2|12*D|2|4*D|14|4*M|0|21!"
	"M|0|4!"
	"M|0|4!"
	"M|6|4!"
	"M|0|4!"
	"M|7|4!"
	"M|4|4!"
	"M|10|4!"
	"M|3|4!"
	"M|14|4!"
	"M|18|4!"
	"M|5|4!"
	"M|8|4!"
	"M|2|4!"
	"M|13|4!"
	"M|11|4!"
	"M|0|4!"
	"M|3|4!"
	"M|3|25*D|2|18*D|4|25*M|0|21!"
	"M|3|25*D|2|18*D|4|25*M|0|21!"
	"M|3|25*D|2|18*D|4|25*M|11|25*D|10|18*D|12|25*M|0|21!"
	"M|3|25*D|2|18*D|4|25*M|11|25*D|10|18*D|12|25*M|0|21!"
	"M|16|4!"
	"M|13|4!"
	"M|15|4!"
	"M|16|4!"
	"M|19|4!"
	"M|4|4!"
	"M|5|9*D|4|11*D|4|13*D|5|15*D|6|16*D|8|17*D|10|17*D|12|16*D|13|15*D|14|13*D|14|11*D|13|9*D|12|8*D|10|7*D|8|7*D|6|8*D|5|9*M|3|6*D|15|18*M|0|21!"
	"M|8|4!"
	"M|19|4!"
	"M|16|4!"
	"M|18|4!"
	"M|16|4!"
	"M|9|4!"
	"M|12|4!"
	"M|13|4!"
	"M|11|4!"
	"M|10|4!"
	"M|14|4!"
	"M|2|4!"
	"M|5|25*D|5|4*M|6|25*D|6|4*M|12|19*D|12|11*M|2|25*D|18|25*D|18|19*D|17|25*M|6|15*D|12|15*M|2|4*D|18|4*D|18|10*D|17|4*M|7|27*D|6|28*D|7|29*D|8|28*D|7|27*M|13|27*D|12|28*D|13|29*D|14|28*D|13|27*M|0|21!"
	"M|8|4!"
	"M|2|4!"
	"M|10|19*D|4|13*D|10|7*M|16|19*D|10|13*D|16|7*M|8|17*D|5|13*D|8|9*M|14|17*D|11|13*D|14|9*M|0|21!"
	"M|13|4!"
	"M|9|4!"
	"M|9|4!"
	"M|11|4!"
	"M|7|25*D|5|24*D|4|22*D|4|20*D|6|18*D|8|18*D|10|19*D|11|21*D|11|23*D|9|25*D|7|25*M|5|24*D|5|19*M|10|24*D|10|19*M|0|21!"
	"M|4|17*D|14|17*M|9|22*D|9|12*M|4|9*D|14|9*M|0|21!"
	"M|6|4!"
	"M|17|4!"
	"M|5|4!"
	"M|3|4!"
	"M|8|4!"
	"M|13|4!"
	"M|8|4*D|6|5*D|4|7*D|3|10*D|3|12*D|15|12*D|15|14*D|14|16*D|13|17*D|11|18*D|8|18*D|5|17*D|3|15*D|2|12*D|2|10*D|3|7*D|5|5*D|8|4*D|10|4*D|13|5*D|15|7*M|14|12*D|14|15*D|13|17*M|8|18*D|6|17*D|4|15*D|3|12*M|6|20*D|5|21*D|6|22*D|7|21*D|6|20*M|12|20*D|11|21*D|12|22*D|13|21*D|12|20*M|0|21!"
	"M|5|25*D|5|4*M|2|25*D|6|25*D|18|6*M|6|23*D|18|4*D|18|25*M|15|25*D|21|25*M|2|4*D|8|4*M|26|13*D|24|14*D|23|16*D|23|18*D|24|20*D|26|21*D|28|21*D|30|20*D|31|18*D|31|16*D|30|14*D|28|13*D|26|13*M|23|10*D|31|10*M|24|20*D|24|14*M|30|20*D|30|14*M|0|21!"
	"M|3|4!"
	"M|4|19*D|10|13*D|4|7*M|10|19*D|16|13*D|10|7*M|12|17*D|15|13*D|12|9*M|6|17*D|9|13*D|6|9*M|0|21!"
	"M|10|4!"
	"M|12|4!"
	"M|12|4!"
	"M|0|4!"
	"M|17|4*D|10|25*D|3|4*M|10|22*D|16|4*M|5|10*D|14|10*M|1|4*D|7|4*M|13|4*D|19|4*M|0|21!"
	"M|5|25*D|5|4*M|6|25*D|6|4*M|16|25*D|17|19*D|17|25*D|2|25*M|6|15*D|14|15*D|17|14*D|18|13*D|19|11*D|19|8*D|18|6*D|17|5*D|14|4*D|2|4*M|14|15*D|16|14*D|17|13*D|18|11*D|18|8*D|17|6*D|16|5*D|14|4*M|0|21!"
	"M|5|25*D|5|4*M|6|25*D|6|4*M|2|25*D|14|25*D|17|24*D|18|23*D|19|21*D|19|19*D|18|17*D|17|16*D|14|15*D|17|14*D|18|13*D|19|11*D|19|8*D|18|6*D|17|5*D|14|4*D|2|4*M|14|25*D|16|24*D|17|23*D|18|21*D|18|19*D|17|17*D|16|16*D|14|15*D|16|14*D|17|13*D|18|11*D|18|8*D|17|6*D|16|5*D|14|4*M|6|15*D|14|15*M|0|21!"
	"M|5|4*D|5|25*M|6|4*D|6|25*M|2|4*D|9|4*M|2|25*D|17|25*D|17|19*D|16|25*M|0|21!"
	"M|2|4*D|1|-2*D|1|4*D|21|4*D|21|-2*D|20|4*M|17|25*D|17|4*M|18|25*D|18|4*M|7|25*D|7|8*D|6|5*D|4|4*D|5|5*D|6|8*D|6|25*M|3|25*D|21|25*M|0|21!"
	"M|5|25*D|5|4*M|6|25*D|6|4*M|12|19*D|12|11*M|2|25*D|18|25*D|18|19*D|17|25*M|6|15*D|12|15*M|2|4*D|18|4*D|18|10*D|17|4*M|0|21!"
	"M|17|25*D|17|4*M|18|25*D|18|4*M|31|25*D|18|12*M|23|16*D|31|4*M|22|16*D|30|4*M|14|25*D|21|25*M|27|25*D|33|25*M|14|4*D|21|4*M|27|4*D|33|4*M|12|16*D|4|4*M|13|16*D|5|4*M|8|25*D|2|25*M|8|4*D|2|4*M|4|25*D|17|12*M|0|21!"
	"M|3|22*D|2|25*D|2|19*D|3|22*D|5|24*D|8|25*D|11|25*D|15|24*D|16|22*D|16|19*D|15|17*D|12|16*D|9|16*M|14|24*D|15|22*D|15|19*D|14|17*D|12|16*D|14|15*D|16|13*D|17|11*D|17|8*D|16|6*D|15|5*D|11|4*D|14|5*D|15|6*D|16|8*D|16|11*D|15|14*M|11|4*D|7|4*D|4|5*D|3|6*D|2|8*M|0|21!"
	"M|5|25*D|5|4*M|6|25*D|6|4*M|18|25*D|18|4*M|19|25*D|19|4*M|2|25*D|9|25*M|15|25*D|22|25*M|2|4*D|9|4*M|15|4*D|22|4*M|18|23*D|6|6*M|0|21!"
	"M|5|25*D|5|4*M|6|25*D|6|4*M|18|25*D|18|4*M|19|25*D|19|4*M|2|25*D|9|25*M|15|25*D|22|25*M|2|4*D|9|4*M|15|4*D|22|4*M|18|23*D|6|6*M|10|29*D|9|28*D|10|27*D|11|28*D|10|29*M|10|27*D|12|27*D|16|29*M|0|21!"
	"M|5|25*D|5|4*M|6|25*D|6|4*M|19|25*D|6|12*M|11|16*D|19|4*M|10|16*D|18|4*M|2|25*D|9|25*M|15|25*D|21|25*M|2|4*D|9|4*M|15|4*D|21|4*M|0|21!"
	"M|9|25*D|9|8*D|8|5*D|6|4*D|4|4*D|2|5*D|1|7*D|1|9*D|2|10*D|3|9*D|2|8*M|8|25*D|8|8*D|7|5*D|6|4*M|17|25*D|17|4*M|18|25*D|18|4*M|14|4*D|21|4*M|5|25*D|21|25*M|0|21!"
	"M|19|4*D|19|25*D|12|4*D|5|25*D|5|4*M|2|25*D|6|25*D|12|7*M|20|25*D|20|4*M|19|25*D|23|25*M|2|4*D|8|4*M|16|4*D|23|4*M|0|21!"
	"M|5|25*D|5|4*M|6|25*D|6|4*M|18|25*D|18|4*M|19|25*D|19|4*M|2|25*D|9|25*M|15|25*D|22|25*M|6|15*D|18|15*M|2|4*D|9|4*M|15|4*D|22|4*M|0|21!"
	"M|9|25*D|6|24*D|4|22*D|3|20*D|2|16*D|2|13*D|3|9*D|4|7*D|6|5*D|9|4*D|11|4*D|14|5*D|16|7*D|17|9*D|18|13*D|18|16*D|17|20*D|16|22*D|14|24*D|11|25*D|9|25*D|7|24*D|5|22*D|4|20*D|3|16*D|3|13*D|4|9*D|5|7*D|7|5*D|9|4*M|11|4*D|13|5*D|15|7*D|16|9*D|17|13*D|17|16*D|16|20*D|15|22*D|13|24*D|11|25*M|0|21!"
	"M|5|25*D|5|4*M|6|25*D|6|4*M|2|4*D|9|4*M|19|25*D|19|4*M|20|25*D|20|4*M|16|4*D|23|4*M|2|25*D|23|25*M|0|21!"
	"M|5|25*D|5|4*M|6|25*D|6|4*M|2|25*D|14|25*D|17|24*D|18|23*D|19|21*D|19|18*D|18|16*D|17|15*D|14|14*D|6|14*M|14|25*D|16|24*D|17|23*D|18|21*D|18|18*D|17|16*D|16|15*D|14|14*M|2|4*D|9|4*M|0|21!"
	"M|16|22*D|17|19*D|17|25*D|16|22*D|14|24*D|11|25*D|9|25*D|6|24*D|4|22*D|3|20*D|2|17*D|2|12*D|3|9*D|4|7*D|6|5*D|9|4*D|11|4*D|14|5*D|16|7*D|17|9*M|9|25*D|7|24*D|5|22*D|4|20*D|3|17*D|3|12*D|4|9*D|5|7*D|7|5*D|9|4*M|0|21!"
	"M|8|25*D|8|4*M|9|25*D|9|4*M|2|25*D|1|19*D|1|25*D|16|25*D|16|19*D|15|25*M|5|4*D|12|4*M|0|21!"
	"M|19|25*D|13|11*D|11|7*D|9|5*D|7|4*D|6|4*D|5|5*D|6|6*D|7|5*M|15|25*D|21|25*M|1|25*D|7|25*M|12|9*D|3|25*M|12|11*D|4|25*M|0|21!"
	"M|14|25*D|14|4*M|15|25*D|15|4*M|11|25*D|18|25*M|11|4*D|18|4*M|22|10*D|24|11*D|25|12*D|26|14*D|26|17*D|25|19*D|24|20*D|22|21*D|25|20*D|26|19*D|27|17*D|27|14*D|26|12*D|25|11*D|22|10*D|15|10*M|22|21*D|15|21*M|7|10*D|5|11*D|4|12*D|3|14*D|3|17*D|4|19*D|5|20*D|7|21*D|4|20*D|3|19*D|2|17*D|2|14*D|3|12*D|4|11*D|7|10*D|14|10*M|7|21*D|14|21*M|0|21!"
	"M|4|25*D|17|4*M|5|25*D|18|4*M|18|25*D|4|4*M|2|25*D|8|25*M|14|25*D|20|25*M|2|4*D|8|4*M|14|4*D|20|4*M|0|21!"
	"M|5|4*D|5|25*M|6|4*D|6|25*M|2|25*D|9|25*M|19|4*D|19|25*M|20|4*D|20|25*M|16|25*D|23|25*M|2|4*D|23|4*D|23|-2*D|22|4*M|0|21!"
	"M|14|25*D|21|25*M|18|25*D|18|4*M|17|25*D|17|4*M|14|4*D|21|4*M|1|25*D|8|25*M|4|25*D|4|17*D|6|15*D|9|14*D|12|14*D|17|16*M|5|25*D|5|17*D|7|15*D|9|14*M|0|21!"
	"M|5|4*D|5|25*M|6|4*D|6|25*M|2|25*D|9|25*M|17|4*D|17|25*M|18|4*D|18|25*M|14|25*D|21|25*M|29|4*D|29|25*M|30|4*D|30|25*M|26|25*D|33|25*M|2|4*D|33|4*M|0|21!"
	"M|5|4*D|5|25*M|6|4*D|6|25*M|2|25*D|9|25*M|17|4*D|17|25*M|18|4*D|18|25*M|14|25*D|21|25*M|29|4*D|29|25*M|30|4*D|30|25*M|26|25*D|33|25*M|2|4*D|33|4*D|33|-2*D|32|4*M|0|21!"
	"M|2|25*D|1|19*D|1|25*D|12|25*M|8|4*D|8|25*M|9|4*D|9|25*M|5|4*D|17|4*D|20|5*D|21|6*D|22|8*D|22|11*D|21|13*D|20|14*D|17|15*D|9|15*M|17|4*D|19|5*D|20|6*D|21|8*D|21|11*D|20|13*D|19|14*D|17|15*M|0|21!"
	"M|5|4*D|5|25*M|6|4*D|6|25*M|2|4*D|14|4*D|17|5*D|18|6*D|19|8*D|19|11*D|18|13*D|17|14*D|14|15*D|6|15*M|14|4*D|16|5*D|17|6*D|18|8*D|18|11*D|17|13*D|16|14*D|14|15*M|2|25*D|9|25*M|24|25*D|24|4*M|25|25*D|25|4*M|21|25*D|28|25*M|21|4*D|28|4*M|0|21!"
	"M|5|4*D|5|25*M|6|4*D|6|25*M|2|4*D|14|4*D|17|5*D|18|6*D|19|8*D|19|11*D|18|13*D|17|14*D|14|15*D|6|15*M|14|4*D|16|5*D|17|6*D|18|8*D|18|11*D|17|13*D|16|14*D|14|15*M|2|25*D|9|25*M|0|21!"
	"M|3|22*D|2|19*D|2|25*D|3|22*D|5|24*D|8|25*D|10|25*D|13|24*D|15|22*D|16|20*D|17|17*D|17|12*D|16|9*D|15|7*D|13|5*D|10|4*D|8|4*D|5|5*D|3|7*D|2|9*M|10|25*D|12|24*D|14|22*D|15|20*D|16|17*D|16|12*D|15|9*D|14|7*D|12|5*D|10|4*M|16|15*D|7|15*M|0|21!"
	"M|5|25*D|5|4*M|6|25*D|6|4*M|2|25*D|9|25*M|2|4*D|9|4*M|18|25*D|15|24*D|13|22*D|12|20*D|11|16*D|11|13*D|12|9*D|13|7*D|15|5*D|18|4*D|20|4*D|23|5*D|25|7*D|26|9*D|27|13*D|27|16*D|26|20*D|25|22*D|23|24*D|20|25*D|18|25*D|16|24*D|14|22*D|13|20*D|12|16*D|12|13*D|13|9*D|14|7*D|16|5*D|18|4*M|20|4*D|22|5*D|24|7*D|25|9*D|26|13*D|26|16*D|25|20*D|24|22*D|22|24*D|20|25*M|6|15*D|11|15*M|0|21!"
	"M|17|25*D|17|4*M|16|25*D|16|4*M|20|25*D|8|25*D|5|24*D|4|23*D|3|21*D|3|19*D|4|17*D|5|16*D|8|15*D|16|15*M|8|25*D|6|24*D|5|23*D|4|21*D|4|19*D|5|17*D|6|16*D|8|15*M|20|4*D|13|4*M|2|4*D|8|4*M|5|4*D|11|15*M|6|4*D|12|15*M|0|21!"
	"M|4|16*D|4|15*D|3|15*D|3|16*D|4|17*D|6|18*D|10|18*D|12|17*D|13|16*D|14|14*D|14|7*D|15|5*D|16|4*D|17|4*M|13|16*D|13|7*D|14|5*D|16|4*M|13|14*D|12|13*D|6|12*D|3|11*D|2|9*D|2|7*D|3|5*D|6|4*D|9|4*D|11|5*D|13|7*M|6|12*D|4|11*D|3|9*D|3|7*D|4|5*D|6|4*M|0|21!"
	"M|3|20*D|4|21*D|7|22*D|12|22*D|15|23*D|16|25*D|15|24*D|12|23*D|7|23*D|4|22*D|3|20*D|2|11*D|2|10*D|3|7*D|5|5*D|8|4*D|10|4*D|13|5*D|15|7*D|16|10*D|16|11*D|15|14*D|13|16*D|10|17*D|8|17*D|5|16*D|3|14*D|2|11*M|8|17*D|6|16*D|4|14*D|3|11*D|3|10*D|4|7*D|6|5*D|8|4*M|10|4*D|12|5*D|14|7*D|15|10*D|15|11*D|14|14*D|12|16*D|10|17*M|0|21!"
	"M|5|18*D|5|4*M|6|4*D|6|18*M|12|18*D|15|17*D|16|16*D|16|14*D|15|13*D|12|12*D|14|13*D|15|14*D|15|16*D|14|17*D|12|18*D|2|18*M|17|9*D|16|11*D|13|12*D|15|11*D|16|9*D|16|7*D|15|5*D|13|4*D|16|5*D|17|7*D|17|9*M|6|12*D|13|12*M|2|4*D|13|4*M|0|21!"
	"M|5|18*D|5|4*M|15|18*D|16|13*D|16|18*D|2|18*M|6|18*D|6|4*M|2|4*D|9|4*M|0|21!"
	"M|14|18*D|14|4*M|15|18*D|15|4*M|2|4*D|1|-1*D|1|4*D|18|4*D|18|-1*D|17|4*M|6|18*D|6|7*D|5|5*D|3|4*D|4|5*D|5|7*D|5|18*M|3|18*D|18|18*M|0|21!"
	"M|8|4*D|6|5*D|4|7*D|3|10*D|3|12*D|15|12*D|15|14*D|14|16*D|13|17*D|11|18*D|8|18*D|5|17*D|3|15*D|2|12*D|2|10*D|3|7*D|5|5*D|8|4*D|10|4*D|13|5*D|15|7*M|14|12*D|14|15*D|13|17*M|8|18*D|6|17*D|4|15*D|3|12*M|0|21!"
	"M|26|18*D|16|8*M|21|12*D|27|4*M|20|12*D|26|4*M|23|18*D|29|18*M|12|4*D|19|4*M|23|4*D|29|4*M|12|18*D|19|18*M|16|4*D|16|18*M|5|18*D|15|8*M|10|12*D|4|4*M|11|12*D|5|4*M|8|18*D|2|18*M|8|4*D|2|4*M|15|18*D|15|4*M|0|21!"
	"M|9|18*D|12|17*D|13|16*D|13|14*D|12|13*D|9|12*D|11|13*D|12|14*D|12|16*D|11|17*D|9|18*D|6|18*D|4|17*D|3|16*M|3|7*D|4|8*D|3|9*D|2|8*D|2|7*D|4|5*D|6|4*D|9|4*D|12|5*D|14|7*D|14|9*D|13|11*D|10|12*D|12|11*D|13|9*D|13|7*D|11|5*D|9|4*M|10|12*D|6|12*M|0|21!"
	"M|5|18*D|5|4*M|6|18*D|6|4*M|13|4*D|20|4*M|16|4*D|16|18*M|17|18*D|17|4*M|2|18*D|9|18*M|2|4*D|9|4*M|13|18*D|20|18*M|16|17*D|6|5*M|0|21!"
	"M|5|18*D|5|4*M|6|18*D|6|4*M|13|4*D|20|4*M|16|4*D|16|18*M|17|18*D|17|4*M|2|18*D|9|18*M|2|4*D|9|4*M|13|18*D|20|18*M|16|17*D|6|5*M|9|22*D|8|21*D|9|20*D|10|21*D|9|22*M|9|20*D|11|20*D|15|22*M|0|21!"
	"M|16|18*D|6|8*M|11|12*D|17|4*M|10|12*D|16|4*M|13|18*D|19|18*M|2|4*D|9|4*M|13|4*D|19|4*M|2|18*D|9|18*M|5|4*D|5|18*M|6|4*D|6|18*M|0|21!"
	"M|7|18*D|7|7*D|6|5*D|4|4*D|2|4*D|1|5*D|1|6*D|2|7*D|3|6*D|2|5*M|6|18*D|6|7*D|5|5*D|4|4*M|14|18*D|14|4*M|15|18*D|15|4*M|11|4*D|18|4*M|18|18*D|4|18*M|0|21!"
	"M|2|4*D|8|4*M|5|4*D|5|18*D|11|4*D|17|18*D|17|4*M|2|18*D|6|18*D|11|6*M|18|18*D|18|4*M|14|4*D|21|4*M|17|18*D|21|18*M|0|21!"
	"M|5|18*D|5|4*M|6|18*D|6|4*M|2|4*D|9|4*M|2|18*D|9|18*M|6|12*D|15|12*M|12|4*D|19|4*M|15|4*D|15|18*M|16|18*D|16|4*M|12|18*D|19|18*M|0|21!"
	"M|8|18*D|5|17*D|3|15*D|2|12*D|2|10*D|3|7*D|5|5*D|8|4*D|10|4*D|13|5*D|15|7*D|16|10*D|16|12*D|15|15*D|13|17*D|10|18*D|8|18*D|6|17*D|4|15*D|3|12*D|3|10*D|4|7*D|6|5*D|8|4*M|10|4*D|12|5*D|14|7*D|15|10*D|15|12*D|14|15*D|12|17*D|10|18*M|0|21!"
	"M|5|18*D|5|4*M|6|18*D|6|4*M|2|4*D|9|4*M|14|4*D|21|4*M|17|4*D|17|18*M|18|18*D|18|4*M|2|18*D|21|18*M|0|21!"
	"M|5|18*D|5|-3*M|2|18*D|6|18*D|6|-3*M|6|15*D|8|17*D|10|18*D|12|18*D|15|17*D|17|15*D|18|12*D|18|10*D|17|7*D|15|5*D|12|4*D|10|4*D|8|5*D|6|7*M|12|18*D|14|17*D|16|15*D|17|12*D|17|10*D|16|7*D|14|5*D|12|4*M|2|-3*D|9|-3*M|0|21!"
	"M|14|15*D|13|14*D|14|13*D|15|14*D|15|15*D|13|17*D|11|18*D|8|18*D|5|17*D|3|15*D|2|12*D|2|10*D|3|7*D|5|5*D|8|4*D|10|4*D|13|5*D|15|7*M|8|18*D|6|17*D|4|15*D|3|12*D|3|10*D|4|7*D|6|5*D|8|4*M|0|21!"
	"M|15|18*D|16|13*D|16|18*D|1|18*D|1|13*D|2|18*M|8|18*D|8|4*M|9|18*D|9|4*M|5|4*D|12|4*M|0|21!"
	"M|3|18*D|9|4*D|7|0*D|5|-2*D|3|-3*D|2|-3*D|1|-2*D|2|-1*D|3|-2*M|4|18*D|9|6*M|15|18*D|9|4*M|1|18*D|7|18*M|11|18*D|17|18*M|0|21!"
	"M|14|15*D|12|17*D|10|18*D|8|18*D|5|17*D|3|15*D|2|12*D|2|10*D|3|7*D|5|5*D|8|4*D|10|4*D|12|5*D|14|7*M|8|18*D|6|17*D|4|15*D|3|12*D|3|10*D|4|7*D|6|5*D|8|4*M|11|-3*D|18|-3*M|15|15*D|17|17*D|19|18*D|21|18*D|24|17*D|26|15*D|27|12*D|27|10*D|26|7*D|24|5*D|21|4*D|19|4*D|17|5*D|15|7*M|21|18*D|23|17*D|25|15*D|26|12*D|26|10*D|25|7*D|23|5*D|21|4*M|14|25*D|14|-3*M|15|-3*D|15|25*D|11|25*M|0|21!"
	"M|4|18*D|15|4*M|5|18*D|16|4*M|16|18*D|4|4*M|2|18*D|8|18*M|12|18*D|18|18*M|2|4*D|8|4*M|12|4*D|18|4*M|0|21!"
	"M|5|4*D|5|18*M|6|4*D|6|18*M|2|18*D|9|18*M|14|18*D|21|18*M|17|18*D|17|4*M|18|4*D|18|18*M|2|4*D|21|4*D|21|-1*D|20|4*M|0|21!"
	"M|5|18*D|5|14*D|6|12*D|8|11*D|11|11*D|15|13*M|15|18*D|15|4*M|16|18*D|16|4*M|4|18*D|4|14*D|5|12*D|8|11*M|1|18*D|8|18*M|12|18*D|19|18*M|12|4*D|19|4*M|0|21!"
	"M|5|4*D|5|18*M|6|4*D|6|18*M|2|18*D|9|18*M|12|18*D|19|18*M|15|18*D|15|4*M|16|4*D|16|18*M|22|18*D|29|18*M|25|18*D|25|4*M|26|4*D|26|18*M|2|4*D|29|4*M|0|21!"
	"M|5|4*D|5|18*M|6|4*D|6|18*M|2|18*D|9|18*M|12|18*D|19|18*M|15|18*D|15|4*M|16|4*D|16|18*M|22|18*D|29|18*M|25|18*D|25|4*M|26|4*D|26|18*M|2|4*D|29|4*D|29|-1*D|28|4*M|0|21!"
	"M|8|18*D|8|4*M|9|4*D|9|18*M|12|18*D|1|18*D|1|13*D|2|18*M|19|9*D|18|11*D|15|12*D|17|11*D|18|9*D|18|7*D|17|5*D|15|4*D|18|5*D|19|7*D|19|9*M|9|12*D|15|12*M|5|4*D|15|4*M|0|21!"
	"M|5|18*D|5|4*M|6|4*D|6|18*M|2|18*D|9|18*M|16|9*D|15|11*D|12|12*D|14|11*D|15|9*D|15|7*D|14|5*D|12|4*D|15|5*D|16|7*D|16|9*M|6|12*D|12|12*M|2|4*D|12|4*M|20|18*D|20|4*M|17|4*D|24|4*M|21|4*D|21|18*M|17|18*D|24|18*M|0|21!"
	"M|5|18*D|5|4*M|6|4*D|6|18*M|2|18*D|9|18*M|16|9*D|15|11*D|12|12*D|14|11*D|15|9*D|15|7*D|14|5*D|12|4*D|15|5*D|16|7*D|16|9*M|6|12*D|12|12*M|2|4*D|12|4*M|0|21!"
	"M|3|15*D|4|14*D|3|13*D|2|14*D|2|15*D|4|17*D|6|18*D|9|18*D|12|17*D|14|15*D|15|12*D|15|10*D|14|7*D|12|5*D|9|4*D|7|4*D|4|5*D|2|7*M|9|18*D|11|17*D|13|15*D|14|12*D|14|10*D|13|7*D|11|5*D|9|4*M|7|12*D|14|12*M|0|21!"
	"M|5|18*D|5|4*M|6|18*D|6|4*M|2|4*D|9|4*M|2|18*D|9|18*M|6|12*D|10|12*D|10|10*D|11|7*D|13|5*D|16|4*D|18|4*D|21|5*D|23|7*D|24|10*D|24|12*D|23|15*D|21|17*D|18|18*D|16|18*D|13|17*D|11|15*D|10|12*M|16|18*D|14|17*D|12|15*D|11|12*D|11|10*D|12|7*D|14|5*D|16|4*M|18|4*D|20|5*D|22|7*D|23|10*D|23|12*D|22|15*D|20|17*D|18|18*M|0|21!"
	"M|6|18*D|3|17*D|2|16*D|2|14*D|3|13*D|6|12*D|4|13*D|3|14*D|3|16*D|4|17*D|6|18*D|16|18*M|4|4*D|8|12*M|5|4*D|9|12*M|13|18*D|13|4*M|12|4*D|12|18*M|9|4*D|16|4*M|6|12*D|12|12*M|2|4*D|6|4*M|0|21";
