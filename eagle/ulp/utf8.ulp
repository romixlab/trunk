// vim:  set foldmethod=marker commentstring=//\ %s :


string codes[] = {// {{{
" ", "32", "!", "33", "\"", "34", "#", "35", "$", "36", "%", "37", "&", "38", "'", "39", "(", "40", ")", "41", "*", "42", "+", "43", ",", "44", "-", "45", ".", "46", "/", "47", "0", "48", "1", "49", "2", "50", "3", "51", "4", "52", "5", "53", "6", "54", "7", "55", "8", "56", "9", "57", ":", "58", ";", "59", "<", "60", "=", "61", ">", "62", "?", "63", "@", "64", "A", "65", "B", "66", "C", "67", "D", "68", "E", "69", "F", "70", "G", "71", "H", "72", "I", "73", "J", "74", "K", "75", "L", "76", "M", "77", "N", "78", "O", "79", "P", "80", "Q", "81", "R", "82", "S", "83", "T", "84", "U", "85", "V", "86", "W", "87", "X", "88", "Y", "89", "Z", "90", "[", "91", "\\", "92", "]", "93", "^", "94", "_", "95", "`", "96", "a", "97", "b", "98", "c", "99", "d", "100", "e", "101", "f", "102", "g", "103", "h", "104", "i", "105", "j", "106", "k", "107", "l", "108", "m", "109", "n", "110", "o", "111", "p", "112", "q", "113", "r", "114", "s", "115", "t", "116", "u", "117", "v", "118", "w", "119", "x", "120", "y", "121", "z", "122", "{", "123", "|", "124", "}", "125", "~", "126", "", "127", "Ђ", "128", "Ѓ", "129", "‚", "130", "ѓ", "131", "„", "132", "…", "133", "†", "134", "‡", "135", "€", "136", "‰", "137", "Љ", "138", "‹", "139", "Њ", "140", "Ќ", "141", "Ћ", "142", "Џ", "143", "ђ", "144", "‘", "145", "’", "146", "“", "147", "”", "148", "•", "149", "–", "150", "—", "151", "", "152", "™", "153", "љ", "154", "›", "155", "њ", "156", "ќ", "157", "ћ", "158", "џ", "159", " ", "160", "Ў", "161", "ў", "162", "Ј", "163", "¤", "164", "Ґ", "165", "¦", "166", "§", "167", "Ё", "168", "©", "169", "Є", "170", "«", "171", "¬", "172", "­", "173", "®", "174", "Ї", "175", "°", "176", "±", "177", "І", "178", "і", "179", "ґ", "180", "µ", "181", "¶", "182", "·", "183", "ё", "184", "№", "185", "є", "186", "»", "187", "ј", "188", "Ѕ", "189", "ѕ", "190", "ї", "191", "А", "192", "Б", "193", "В", "194", "Г", "195", "Д", "196", "Е", "197", "Ж", "198", "З", "199", "И", "200", "Й", "201", "К", "202", "Л", "203", "М", "204", "Н", "205", "О", "206", "П", "207", "Р", "208", "С", "209", "Т", "210", "У", "211", "Ф", "212", "Х", "213", "Ц", "214", "Ч", "215", "Ш", "216", "Щ", "217", "Ъ", "218", "Ы", "219", "Ь", "220", "Э", "221", "Ю", "222", "Я", "223", "а", "224", "б", "225", "в", "226", "г", "227", "д", "228", "е", "229", "ж", "230", "з", "231", "и", "232", "й", "233", "к", "234", "л", "235", "м", "236", "н", "237", "о", "238", "п", "239", "р", "240", "с", "241", "т", "242", "у", "243", "ф", "244", "х", "245", "ц", "246", "ч", "247", "ш", "248", "щ", "249", "ъ", "250", "ы", "251", "ь", "252", "э", "253", "ю", "254", "я", "255"
};// }}}

#include "rusfont.ulp"
